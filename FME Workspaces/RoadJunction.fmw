FME workspace RoadJunction.fmw

Parameters:
- SourceDataset_RoadJunction = $(ROADS_DATA_INPUT_FOLDER)\Highways_Rrami_RoadJunction_*.gml*   # Source RoadJunction GML File(s)
- DestDataset_RoadJunction = $(MIDDLE_FOLDER)\RoadJunction.gpkg   # Middle RoadJunction Geopackage File

Readers:
- GML_1: GML from $(SourceDataset_RoadJunction) in EPSG:27700

Writers:
- GEOPACKAGE_1: GEOPACKAGE to $(DestDataset_RoadJunction)

RoadJunction (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, reasonForChange xml_buffer, reasonForChange.codeSpace xml_buffer, junctionType xml_buffer, junctionType.codeSpace xml_buffer, junctionName{} xml_buffer, junctionName{}.xml_lang xml_buffer, roadClassificationNumber xml_buffer, junctionNumber xml_buffer, node{}.nilReason xml_buffer, node{}.gml_remoteSchema xml_buffer, node{}.xlink_href xml_buffer, node{}.owns xml_boolean
    -> DateFormatter
    -> ListExploder
RoadJunction (writer GEOPACKAGE_1)
    attributes: TOID text(20), identifier text(37), beginLifespanVersion text(20), reasonForChange text(32), junctionType text(26), junctionName1 text(120), junctionName2 text(120), roadClassificationNumber text(7), junctionNumber text(3), chunkname text(50)
RoadJunctionNode (writer GEOPACKAGE_1)
    attributes: TOID text(20), node text(20)

Bookmark: Create roadJuntion attribution
DateFormatter
    DATE_ATTR = beginLifespanVersion
    FMT = FME Date (%Y%m%d)
    INVALID_DATE_VALUE = _FME_NO_OP_
    SRCFMT = Unknown - Automatic Detection
    -> StringReplacer
StringReplacer
    CASE = NO
    FIND_TEXT = T00:00:00.000
    NO_MATCH = _FME_NO_OP_
    REGEXP = NO
    REPLACE_TEXT = 000000
    SRC_ATTRS = beginLifespanVersion
    -> AttributeRenamer
AttributeRenamer
    ATTR_TABLE:
      RENAME_SET_DEFAULT gml_id > TOID
      RENAME_SET_DEFAULT inspireId.Identifier.localId > identifier
      RENAME_SET_DEFAULT junctionName{0} > junctionName1
      RENAME_SET_DEFAULT junctionName{1} > junctionName2
      RENAME_SET_DEFAULT fme_basename > chunkname
    -> AttributeManager_2
AttributeManager_2
    ATTR_TABLE:
      REMOVE beginLifespanVersion.nilReason
      REMOVE beginLifespanVersion.xsi_nil
      REMOVE inspireId.Identifier.namespace
      REMOVE inspireId.Identifier.versionId
      REMOVE inspireId.Identifier.versionId.nilReason
      REMOVE inspireId.Identifier.versionId.xsi_nil
      REMOVE endLifespanVersion
      REMOVE endLifespanVersion.nilReason
      REMOVE endLifespanVersion.xsi_nil
      REMOVE inNetwork{}.owns
      REMOVE inNetwork{}.nilReason
      REMOVE inNetwork{}.gml_remoteSchema
      REMOVE inNetwork{}.xlink_href
      REMOVE inNetwork{}.xsi_nil
      REMOVE reasonForChange.codeSpace
      REMOVE junctionType.codeSpace
      REMOVE junctionName{}
      REMOVE junctionName{}.xml_lang
      REMOVE node{}.nilReason
      REMOVE node{}.gml_remoteSchema
      REMOVE node{}.xlink_href
      REMOVE node{}.owns
    -> RoadJunction (writer GEOPACKAGE_1)

Bookmark: Create link table for road node references
ListExploder
    ATTR_ACCUM_MODE = Merge List Attributes
    ATTR_CONFLICT_RES = Use List Attribute Values
    INDEX_ATTR = _element_index
    LIST_ATTR = node{}
    ELEMENTS -> AttributeManager
AttributeManager
    ATTR_TABLE:
      REMOVE beginLifespanVersion
      REMOVE beginLifespanVersion.nilReason
      REMOVE beginLifespanVersion.xsi_nil
      REMOVE inspireId.Identifier.localId
      REMOVE inspireId.Identifier.namespace
      REMOVE inspireId.Identifier.versionId
      REMOVE inspireId.Identifier.versionId.nilReason
      REMOVE inspireId.Identifier.versionId.xsi_nil
      REMOVE endLifespanVersion
      REMOVE endLifespanVersion.nilReason
      REMOVE endLifespanVersion.xsi_nil
      REMOVE inNetwork{}.owns
      REMOVE inNetwork{}.nilReason
      REMOVE inNetwork{}.gml_remoteSchema
      REMOVE inNetwork{}.xlink_href
      REMOVE inNetwork{}.xsi_nil
      REMOVE reasonForChange
      REMOVE reasonForChange.codeSpace
      REMOVE junctionType
      REMOVE junctionType.codeSpace
      REMOVE junctionName{}
      REMOVE junctionName{}.xml_lang
      REMOVE roadClassificationNumber
      REMOVE junctionNumber
      REMOVE nilReason
      REMOVE gml_remoteSchema
      RENAME_SET_VALUE xlink_href > node
      REMOVE owns
      RENAME_SET_VALUE gml_id > TOID
      REMOVE _element_index
    -> AttributeTrimmer
AttributeTrimmer
    SRC_ATTRS = node
    TRIM_CHARS = #
    TRIM_TO_NONE = Yes
    TRIM_TYPE = Left
    -> RoadJunctionNode (writer GEOPACKAGE_1)
