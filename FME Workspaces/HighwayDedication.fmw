FME workspace HighwayDedication.fmw

Parameters:
- SourceDataset_GML = $(DATA_INPUT_FOLDER)\Highways_*_Dedication_*.gml*   # Source HighwayDedication GML File(s)
- DestDataset_GEOPACKAGE = $(MIDDLE_FOLDER)\Dedication.gpkg   # Middle Dedication Geopackage File

Readers:
- GML_1: GML from $(SourceDataset_GML) in EPSG:27700

Writers:
- GEOPACKAGE_1: GEOPACKAGE to $(DestDataset_GEOPACKAGE)

Note: Change location of input GML files
HighwayDedication (reader GML_1)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer, networkRef{}.LinkReference.applicableDirection.xsi_nil xml_boolean, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean, networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean,
      networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer, networkRef{}.PointReference.offset.xsi_nil xml_boolean, networkRef{}.PointReference.atPositionGeometry xml_geometry, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64,
      networkRef{}.SimpleLinearReference.offset.nilReason xml_buffer, networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer, networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NetworkReferenceLocation.locationLine xml_geometry,
      networkRef{}.NetworkReferenceLocation.locationArea xml_geometry, networkRef{}.NodeReference.element.owns xml_boolean, networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, reasonForChange xml_buffer, reasonForChange.codeSpace xml_buffer, dedication xml_buffer,
      dedication.codeSpace xml_buffer, timeInterval{}.TemporalPropertyType.namedDate{} xml_buffer, timeInterval{}.TemporalPropertyType.namedDate{}.codeSpace xml_buffer, timeInterval{}.TemporalPropertyType.dateRange{}.DateRangeType.startDate xml_date, timeInterval{}.TemporalPropertyType.dateRange{}.DateRangeType.endDate xml_date, timeInterval{}.TemporalPropertyType.dateRange{}.DateRangeType.startMonthDay xml_buffer, timeInterval{}.TemporalPropertyType.dateRange{}.DateRangeType.endMonthDay xml_buffer, timeInterval{}.TemporalPropertyType.dayPeriod{}.DayPropertyType.namedDay{} xml_buffer, timeInterval{}.TemporalPropertyType.dayPeriod{}.DayPropertyType.namedDay{}.codeSpace xml_buffer, timeInterval{}.TemporalPropertyType.dayPeriod{}.DayPropertyType.namedPeriod{} xml_buffer, timeInterval{}.TemporalPropertyType.dayPeriod{}.DayPropertyType.namedPeriod{}.codeSpace xml_buffer, timeInterval{}.TemporalPropertyType.dayPeriod{}.DayPropertyType.timePeriod{}.TimePropertyType.namedTime{} xml_buffer, timeInterval{}.TemporalPropertyType.dayPeriod{}.DayPropertyType.timePeriod{}.TimePropertyType.namedTime{}.codeSpace xml_buffer, timeInterval{}.TemporalPropertyType.dayPeriod{}.DayPropertyType.timePeriod{}.TimePropertyType.timeRange{}.TimeRangeType.startTime xml_time, timeInterval{}.TemporalPropertyType.dayPeriod{}.DayPropertyType.timePeriod{}.TimePropertyType.timeRange{}.TimeRangeType.endTime xml_time, publicRightOfWay xml_boolean, nationalCycleRoute xml_boolean, quietRoute xml_boolean, obstruction xml_boolean, planningOrder xml_boolean, worksProhibited xml_boolean, geometry xml_geometry
    -> DateFormatter
    -> ListExploder
    -> ListExploder_8
Note: Cross references
Note: Writer can be changed depending on output requirements
Network_Reference (writer GEOPACKAGE_1)
    attributes: gml_id text(2048), networkRef___LinkReference_element_xlink_href text(2048)

Bookmark: Create Highways Dedication geometry
Note: Reset dates
DateFormatter
    DATE_ATTR = beginLifespanVersion
    FMT = FME Date (%Y%m%d)
    INVALID_DATE_VALUE = _FME_NO_OP_
    SRCFMT = Unknown - Automatic Detection
    -> DateFormatter_2
DateFormatter_2
    DATE_ATTR = validFrom
    FMT = FME Date (%Y%m%d)
    INVALID_DATE_VALUE = _FME_NO_OP_
    SRCFMT = Unknown - Automatic Detection
    -> StringReplacer
StringReplacer
    CASE = NO
    FIND_TEXT = T00:00:00.000
    NO_MATCH = _FME_NO_OP_
    REGEXP = NO
    REPLACE_TEXT = 000000
    SRC_ATTRS = beginLifespanVersion
    -> AttributeRenamer
Note: Rename ids
AttributeRenamer
    ATTR_TABLE:
      RENAME_SET_DEFAULT gml_id > id
      RENAME_SET_DEFAULT inspireId.Identifier.localId > identifier
    -> AttributeManager
AttributeManager
    ATTR_TABLE:
      REMOVE networkRef{}.nilReason
      REMOVE networkRef{}.xsi_nil
      REMOVE networkRef{}.NetworkReference.element.owns
      REMOVE networkRef{}.NetworkReference.element.nilReason
      REMOVE networkRef{}.NetworkReference.element.gml_remoteSchema
      REMOVE networkRef{}.NetworkReference.element.xlink_href
      REMOVE networkRef{}.LinkReference.element.owns
      REMOVE networkRef{}.LinkReference.element.nilReason
      REMOVE networkRef{}.LinkReference.element.gml_remoteSchema
      REMOVE networkRef{}.LinkReference.element.xlink_href
      REMOVE networkRef{}.LinkReference.applicableDirection.owns
      REMOVE networkRef{}.LinkReference.applicableDirection.nilReason
      REMOVE networkRef{}.LinkReference.applicableDirection.gml_remoteSchema
      REMOVE networkRef{}.LinkReference.applicableDirection.xlink_href
      REMOVE networkRef{}.LinkReference.applicableDirection.xsi_nil
      REMOVE networkRef{}.SimplePointReference.element.owns
      REMOVE networkRef{}.SimplePointReference.element.nilReason
      REMOVE networkRef{}.SimplePointReference.element.gml_remoteSchema
      REMOVE networkRef{}.SimplePointReference.element.xlink_href
      REMOVE networkRef{}.SimplePointReference.applicableDirection.owns
      REMOVE networkRef{}.SimplePointReference.applicableDirection.nilReason
      REMOVE networkRef{}.SimplePointReference.applicableDirection.gml_remoteSchema
      REMOVE networkRef{}.SimplePointReference.applicableDirection.xlink_href
      REMOVE networkRef{}.SimplePointReference.applicableDirection.xsi_nil
      REMOVE networkRef{}.SimplePointReference.atPosition
      REMOVE networkRef{}.SimplePointReference.atPosition.uom
      REMOVE networkRef{}.SimplePointReference.offset
      REMOVE networkRef{}.SimplePointReference.offset.nilReason
      REMOVE networkRef{}.SimplePointReference.offset.uom
      REMOVE networkRef{}.SimplePointReference.offset.xsi_nil
      REMOVE networkRef{}.PointReference.element.owns
      REMOVE networkRef{}.PointReference.element.nilReason
      REMOVE networkRef{}.PointReference.element.gml_remoteSchema
      REMOVE networkRef{}.PointReference.element.xlink_href
      REMOVE networkRef{}.PointReference.applicableDirection.owns
      REMOVE networkRef{}.PointReference.applicableDirection.nilReason
      REMOVE networkRef{}.PointReference.applicableDirection.gml_remoteSchema
      REMOVE networkRef{}.PointReference.applicableDirection.xlink_href
      REMOVE networkRef{}.PointReference.applicableDirection.xsi_nil
      REMOVE networkRef{}.PointReference.atPosition
      REMOVE networkRef{}.PointReference.atPosition.uom
      REMOVE networkRef{}.PointReference.offset
      REMOVE networkRef{}.PointReference.offset.nilReason
      REMOVE networkRef{}.PointReference.offset.uom
      REMOVE networkRef{}.PointReference.offset.xsi_nil
      REMOVE networkRef{}.PointReference.atPositionGeometry
      REMOVE networkRef{}.SimpleLinearReference.element.owns
      REMOVE networkRef{}.SimpleLinearReference.element.nilReason
      REMOVE networkRef{}.SimpleLinearReference.element.gml_remoteSchema
      REMOVE networkRef{}.SimpleLinearReference.element.xlink_href
      REMOVE networkRef{}.SimpleLinearReference.applicableDirection.owns
      REMOVE networkRef{}.SimpleLinearReference.applicableDirection.nilReason
      REMOVE networkRef{}.SimpleLinearReference.applicableDirection.gml_remoteSchema
      REMOVE networkRef{}.SimpleLinearReference.applicableDirection.xlink_href
      REMOVE networkRef{}.SimpleLinearReference.applicableDirection.xsi_nil
      REMOVE networkRef{}.SimpleLinearReference.fromPosition
      REMOVE networkRef{}.SimpleLinearReference.fromPosition.uom
      REMOVE networkRef{}.SimpleLinearReference.toPosition
      REMOVE networkRef{}.SimpleLinearReference.toPosition.uom
      REMOVE networkRef{}.SimpleLinearReference.offset
      REMOVE networkRef{}.SimpleLinearReference.offset.nilReason
      REMOVE networkRef{}.SimpleLinearReference.offset.uom
      REMOVE networkRef{}.SimpleLinearReference.offset.xsi_nil
      REMOVE networkRef{}.LinearReference.element.owns
      REMOVE networkRef{}.LinearReference.element.nilReason
      REMOVE networkRef{}.LinearReference.element.gml_remoteSchema
      REMOVE networkRef{}.LinearReference.element.xlink_href
      REMOVE networkRef{}.LinearReference.applicableDirection.owns
      REMOVE networkRef{}.LinearReference.applicableDirection.nilReason
      REMOVE networkRef{}.LinearReference.applicableDirection.gml_remoteSchema
      REMOVE networkRef{}.LinearReference.applicableDirection.xlink_href
      REMOVE networkRef{}.LinearReference.applicableDirection.xsi_nil
      REMOVE networkRef{}.LinearReference.fromPosition
      REMOVE networkRef{}.LinearReference.fromPosition.uom
      REMOVE networkRef{}.LinearReference.toPosition
      REMOVE networkRef{}.LinearReference.toPosition.uom
      REMOVE networkRef{}.LinearReference.offset
      REMOVE networkRef{}.LinearReference.offset.nilReason
      REMOVE networkRef{}.LinearReference.offset.uom
      REMOVE networkRef{}.LinearReference.offset.xsi_nil
      REMOVE networkRef{}.LinearReference.fromPositionGeometry
      REMOVE networkRef{}.LinearReference.toPositionGeometry
      REMOVE networkRef{}.NetworkReferenceLocation.element.owns
      REMOVE networkRef{}.NetworkReferenceLocation.element.nilReason
      REMOVE networkRef{}.NetworkReferenceLocation.element.gml_remoteSchema
      REMOVE networkRef{}.NetworkReferenceLocation.element.xlink_href
      REMOVE networkRef{}.NetworkReferenceLocation.locationDescription
      REMOVE networkRef{}.NetworkReferenceLocation.locationStart
      REMOVE networkRef{}.NetworkReferenceLocation.locationEnd
      REMOVE networkRef{}.NetworkReferenceLocation.locationLine
      REMOVE networkRef{}.NetworkReferenceLocation.locationArea
      REMOVE networkRef{}.NodeReference.element.owns
      REMOVE networkRef{}.NodeReference.element.nilReason
      REMOVE networkRef{}.NodeReference.element.gml_remoteSchema
      REMOVE networkRef{}.NodeReference.element.xlink_href
      REMOVE networkRef{}.NodeReference.location
      REMOVE networkRef{}.NodeReference.linkReference{}.nilReason
      REMOVE networkRef{}.NodeReference.linkReference{}.gml_remoteSchema
      REMOVE networkRef{}.NodeReference.linkReference{}.xlink_href
      REMOVE networkRef{}.NodeReference.linkReference{}.owns
      REMOVE inspireId.Identifier.namespace
      REMOVE inspireId.Identifier.versionId
      REMOVE inspireId.Identifier.versionId.nilReason
      REMOVE inspireId.Identifier.versionId.xsi_nil
      REMOVE beginLifespanVersion.nilReason
      REMOVE beginLifespanVersion.xsi_nil
      REMOVE endLifespanVersion
      REMOVE endLifespanVersion.nilReason
      REMOVE endLifespanVersion.xsi_nil
      REMOVE validFrom.nilReason
      REMOVE validFrom.xsi_nil
      REMOVE validTo
      REMOVE validTo.nilReason
      REMOVE validTo.xsi_nil
      REMOVE reasonForChange.codeSpace
      REMOVE dedication.codeSpace
      REMOVE timeInterval{}.TemporalPropertyType.namedDate{}
      REMOVE timeInterval{}.TemporalPropertyType.namedDate{}.codeSpace
      REMOVE timeInterval{}.TemporalPropertyType.dateRange{}.DateRangeType.startDate
      REMOVE timeInterval{}.TemporalPropertyType.dateRange{}.DateRangeType.endDate
      REMOVE timeInterval{}.TemporalPropertyType.dateRange{}.DateRangeType.startMonthDay
      REMOVE timeInterval{}.TemporalPropertyType.dateRange{}.DateRangeType.endMonthDay
      REMOVE timeInterval{}.TemporalPropertyType.dayPeriod{}.DayPropertyType.namedDay{}
      REMOVE timeInterval{}.TemporalPropertyType.dayPeriod{}.DayPropertyType.namedDay{}.codeSpace
      REMOVE timeInterval{}.TemporalPropertyType.dayPeriod{}.DayPropertyType.namedPeriod{}
      REMOVE timeInterval{}.TemporalPropertyType.dayPeriod{}.DayPropertyType.namedPeriod{}.codeSpace
      REMOVE timeInterval{}.TemporalPropertyType.dayPeriod{}.DayPropertyType.timePeriod{}.TimePropertyType.namedTime{}
      REMOVE timeInterval{}.TemporalPropertyType.dayPeriod{}.DayPropertyType.timePeriod{}.TimePropertyType.namedTime{}.codeSpace
      REMOVE timeInterval{}.TemporalPropertyType.dayPeriod{}.DayPropertyType.timePeriod{}.TimePropertyType.timeRange{}.TimeRangeType.startTime
      REMOVE timeInterval{}.TemporalPropertyType.dayPeriod{}.DayPropertyType.timePeriod{}.TimePropertyType.timeRange{}.TimeRangeType.endTime
    -> AttributeRenamer_25

Bookmark: Manage attributes
AttributeRenamer_25
    ATTR_TABLE:
      RENAME_SET_DEFAULT timeInterval{0}.TemporalPropertyType.namedDate{0} > date000
      RENAME_SET_DEFAULT timeInterval{1}.TemporalPropertyType.namedDate{0} > date100
      RENAME_SET_DEFAULT timeInterval{2}.TemporalPropertyType.namedDate{0} > date200
      RENAME_SET_DEFAULT timeInterval{0}.TemporalPropertyType.namedDate{1} > date001
      RENAME_SET_DEFAULT timeInterval{1}.TemporalPropertyType.namedDate{1} > date101
      RENAME_SET_DEFAULT timeInterval{2}.TemporalPropertyType.namedDate{1} > date201
      RENAME_SET_DEFAULT timeInterval{0}.TemporalPropertyType.namedDate{2} > date002
      RENAME_SET_DEFAULT timeInterval{1}.TemporalPropertyType.namedDate{2} > date102
      RENAME_SET_DEFAULT timeInterval{2}.TemporalPropertyType.namedDate{2} > date202
      RENAME_SET_DEFAULT timeInterval{0}.TemporalPropertyType.dayPeriod{0}.DayPropertyType.namedDay{0} > day000
      RENAME_SET_DEFAULT timeInterval{1}.TemporalPropertyType.dayPeriod{0}.DayPropertyType.namedDay{0} > day100
      RENAME_SET_DEFAULT timeInterval{2}.TemporalPropertyType.dayPeriod{0}.DayPropertyType.namedDay{0} > day200
      RENAME_SET_DEFAULT timeInterval{0}.TemporalPropertyType.dayPeriod{0}.DayPropertyType.namedDay{1} > day001
      RENAME_SET_DEFAULT timeInterval{1}.TemporalPropertyType.dayPeriod{0}.DayPropertyType.namedDay{1} > day101
      RENAME_SET_DEFAULT timeInterval{2}.TemporalPropertyType.dayPeriod{0}.DayPropertyType.namedDay{1} > day201
      RENAME_SET_DEFAULT timeInterval{0}.TemporalPropertyType.dayPeriod{0}.DayPropertyType.namedDay{2} > day002
      RENAME_SET_DEFAULT timeInterval{1}.TemporalPropertyType.dayPeriod{0}.DayPropertyType.namedDay{2} > day102
      RENAME_SET_DEFAULT timeInterval{2}.TemporalPropertyType.dayPeriod{0}.DayPropertyType.namedDay{2} > day202
      RENAME_SET_DEFAULT timeInterval{0}.TemporalPropertyType.dayPeriod{0}.DayPropertyType.namedDay{3} > day003
      RENAME_SET_DEFAULT timeInterval{1}.TemporalPropertyType.dayPeriod{0}.DayPropertyType.namedDay{3} > day103
      RENAME_SET_DEFAULT timeInterval{2}.TemporalPropertyType.dayPeriod{0}.DayPropertyType.namedDay{3} > day203
      RENAME_SET_DEFAULT timeInterval{0}.TemporalPropertyType.dayPeriod{0}.DayPropertyType.namedDay{4} > day004
      RENAME_SET_DEFAULT timeInterval{1}.TemporalPropertyType.dayPeriod{0}.DayPropertyType.namedDay{4} > day104
      RENAME_SET_DEFAULT timeInterval{2}.TemporalPropertyType.dayPeriod{0}.DayPropertyType.namedDay{4} > day204
      RENAME_SET_DEFAULT timeInterval{0}.TemporalPropertyType.dayPeriod{0}.DayPropertyType.namedDay{5} > day005
      RENAME_SET_DEFAULT timeInterval{1}.TemporalPropertyType.dayPeriod{0}.DayPropertyType.namedDay{5} > day105
      RENAME_SET_DEFAULT timeInterval{2}.TemporalPropertyType.dayPeriod{0}.DayPropertyType.namedDay{5} > day205
      RENAME_SET_DEFAULT timeInterval{0}.TemporalPropertyType.dayPeriod{0}.DayPropertyType.namedDay{6} > day006
      RENAME_SET_DEFAULT timeInterval{1}.TemporalPropertyType.dayPeriod{0}.DayPropertyType.namedDay{6} > day106
      RENAME_SET_DEFAULT timeInterval{2}.TemporalPropertyType.dayPeriod{0}.DayPropertyType.namedDay{6} > day206
      RENAME_SET_DEFAULT timeInterval{0}.TemporalPropertyType.dayPeriod{0}.DayPropertyType.namedPeriod{0} > period000
      RENAME_SET_DEFAULT timeInterval{1}.TemporalPropertyType.dayPeriod{0}.DayPropertyType.namedPeriod{0} > period100
      RENAME_SET_DEFAULT timeInterval{2}.TemporalPropertyType.dayPeriod{0}.DayPropertyType.namedPeriod{0} > period200
      RENAME_SET_DEFAULT timeInterval{0}.TemporalPropertyType.dayPeriod{0}.DayPropertyType.namedPeriod{1} > period001
      RENAME_SET_DEFAULT timeInterval{1}.TemporalPropertyType.dayPeriod{0}.DayPropertyType.namedPeriod{1} > period101
      RENAME_SET_DEFAULT timeInterval{2}.TemporalPropertyType.dayPeriod{0}.DayPropertyType.namedPeriod{1} > period201
      RENAME_SET_DEFAULT timeInterval{0}.TemporalPropertyType.dayPeriod{0}.DayPropertyType.namedPeriod{2} > period002
      RENAME_SET_DEFAULT timeInterval{1}.TemporalPropertyType.dayPeriod{0}.DayPropertyType.namedPeriod{2} > period102
      RENAME_SET_DEFAULT timeInterval{2}.TemporalPropertyType.dayPeriod{0}.DayPropertyType.namedPeriod{2} > period202
      RENAME_SET_DEFAULT timeInterval{0}.TemporalPropertyType.dayPeriod{0}.DayPropertyType.timePeriod{0}.TimePropertyType.namedTime{0} > time000
      RENAME_SET_DEFAULT timeInterval{1}.TemporalPropertyType.dayPeriod{0}.DayPropertyType.timePeriod{0}.TimePropertyType.namedTime{0} > time100
      RENAME_SET_DEFAULT timeInterval{2}.TemporalPropertyType.dayPeriod{0}.DayPropertyType.timePeriod{0}.TimePropertyType.namedTime{0} > time200
      RENAME_SET_DEFAULT timeInterval{0}.TemporalPropertyType.dayPeriod{0}.DayPropertyType.timePeriod{0}.TimePropertyType.namedTime{1} > time001
      RENAME_SET_DEFAULT timeInterval{1}.TemporalPropertyType.dayPeriod{0}.DayPropertyType.timePeriod{0}.TimePropertyType.namedTime{1} > time101
      RENAME_SET_DEFAULT timeInterval{2}.TemporalPropertyType.dayPeriod{0}.DayPropertyType.timePeriod{0}.TimePropertyType.namedTime{1} > time201
      RENAME_SET_DEFAULT timeInterval{0}.TemporalPropertyType.dayPeriod{0}.DayPropertyType.timePeriod{0}.TimePropertyType.namedTime{2} > time002
      RENAME_SET_DEFAULT timeInterval{1}.TemporalPropertyType.dayPeriod{0}.DayPropertyType.timePeriod{0}.TimePropertyType.namedTime{2} > time102
      RENAME_SET_DEFAULT timeInterval{2}.TemporalPropertyType.dayPeriod{0}.DayPropertyType.timePeriod{0}.TimePropertyType.namedTime{2} > time202
      RENAME_SET_DEFAULT timeInterval{0}.TemporalPropertyType.dateRange{0}.DateRangeType.startMonthDay > monthdaystart0
      RENAME_SET_DEFAULT timeInterval{1}.TemporalPropertyType.dateRange{0}.DateRangeType.startMonthDay > monthdaystart1
      RENAME_SET_DEFAULT timeInterval{2}.TemporalPropertyType.dateRange{0}.DateRangeType.startMonthDay > monthdaystart2
      RENAME_SET_DEFAULT timeInterval{0}.TemporalPropertyType.dateRange{0}.DateRangeType.endMonthDay > monthdayend0
      RENAME_SET_DEFAULT timeInterval{1}.TemporalPropertyType.dateRange{0}.DateRangeType.endMonthDay > monthdayend1
      RENAME_SET_DEFAULT timeInterval{2}.TemporalPropertyType.dateRange{0}.DateRangeType.startMonthDay > monthdayend2
      RENAME_SET_DEFAULT timeInterval{0}.TemporalPropertyType.dayPeriod{0}.DayPropertyType.timePeriod{0}.TimePropertyType.timeRange{0}.TimeRangeType.startTime > 1sttimestart0
      RENAME_SET_DEFAULT timeInterval{0}.TemporalPropertyType.dayPeriod{0}.DayPropertyType.timePeriod{1}.TimePropertyType.timeRange{0}.TimeRangeType.startTime > 1sttimestart1
      RENAME_SET_DEFAULT timeInterval{0}.TemporalPropertyType.dayPeriod{0}.DayPropertyType.timePeriod{2}.TimePropertyType.timeRange{0}.TimeRangeType.startTime > 1sttimestart2
      RENAME_SET_DEFAULT timeInterval{0}.TemporalPropertyType.dayPeriod{0}.DayPropertyType.timePeriod{3}.TimePropertyType.timeRange{0}.TimeRangeType.startTime > 1sttimestart3
      RENAME_SET_DEFAULT timeInterval{1}.TemporalPropertyType.dayPeriod{0}.DayPropertyType.timePeriod{0}.TimePropertyType.timeRange{0}.TimeRangeType.startTime > 2ndtimestart0
      RENAME_SET_DEFAULT timeInterval{1}.TemporalPropertyType.dayPeriod{0}.DayPropertyType.timePeriod{1}.TimePropertyType.timeRange{0}.TimeRangeType.startTime > 2ndtimestart1
      RENAME_SET_DEFAULT timeInterval{1}.TemporalPropertyType.dayPeriod{0}.DayPropertyType.timePeriod{2}.TimePropertyType.timeRange{0}.TimeRangeType.startTime > 2ndtimestart2
      RENAME_SET_DEFAULT timeInterval{1}.TemporalPropertyType.dayPeriod{0}.DayPropertyType.timePeriod{3}.TimePropertyType.timeRange{0}.TimeRangeType.startTime > 2ndtimestart3
      RENAME_SET_DEFAULT timeInterval{2}.TemporalPropertyType.dayPeriod{0}.DayPropertyType.timePeriod{0}.TimePropertyType.timeRange{0}.TimeRangeType.startTime > 3rdtimestart0
      RENAME_SET_DEFAULT timeInterval{2}.TemporalPropertyType.dayPeriod{0}.DayPropertyType.timePeriod{1}.TimePropertyType.timeRange{0}.TimeRangeType.startTime > 3rdtimestart1
      RENAME_SET_DEFAULT timeInterval{2}.TemporalPropertyType.dayPeriod{0}.DayPropertyType.timePeriod{2}.TimePropertyType.timeRange{0}.TimeRangeType.startTime > 3rdtimestart2
      RENAME_SET_DEFAULT timeInterval{2}.TemporalPropertyType.dayPeriod{0}.DayPropertyType.timePeriod{3}.TimePropertyType.timeRange{0}.TimeRangeType.startTime > 3rdtimestart3
      RENAME_SET_DEFAULT timeInterval{0}.TemporalPropertyType.dayPeriod{0}.DayPropertyType.timePeriod{0}.TimePropertyType.timeRange{0}.TimeRangeType.endTime > 1sttimeend0
      RENAME_SET_DEFAULT timeInterval{0}.TemporalPropertyType.dayPeriod{0}.DayPropertyType.timePeriod{1}.TimePropertyType.timeRange{0}.TimeRangeType.endTime > 1sttimeend1
      RENAME_SET_DEFAULT timeInterval{0}.TemporalPropertyType.dayPeriod{0}.DayPropertyType.timePeriod{2}.TimePropertyType.timeRange{0}.TimeRangeType.endTime > 1sttimeend2
      RENAME_SET_DEFAULT timeInterval{0}.TemporalPropertyType.dayPeriod{0}.DayPropertyType.timePeriod{3}.TimePropertyType.timeRange{0}.TimeRangeType.endTime > 1sttimeend3
      RENAME_SET_DEFAULT timeInterval{1}.TemporalPropertyType.dayPeriod{0}.DayPropertyType.timePeriod{0}.TimePropertyType.timeRange{0}.TimeRangeType.endTime > 2ndtimeend0
      RENAME_SET_DEFAULT timeInterval{1}.TemporalPropertyType.dayPeriod{0}.DayPropertyType.timePeriod{1}.TimePropertyType.timeRange{0}.TimeRangeType.endTime > 2ndtimeend1
      RENAME_SET_DEFAULT timeInterval{1}.TemporalPropertyType.dayPeriod{0}.DayPropertyType.timePeriod{2}.TimePropertyType.timeRange{0}.TimeRangeType.endTime > 2ndtimeend2
      RENAME_SET_DEFAULT timeInterval{1}.TemporalPropertyType.dayPeriod{0}.DayPropertyType.timePeriod{3}.TimePropertyType.timeRange{0}.TimeRangeType.endTime > 2ndtimeend3
      RENAME_SET_DEFAULT timeInterval{2}.TemporalPropertyType.dayPeriod{0}.DayPropertyType.timePeriod{0}.TimePropertyType.timeRange{0}.TimeRangeType.endTime > 3rdtimeend0
      RENAME_SET_DEFAULT timeInterval{2}.TemporalPropertyType.dayPeriod{0}.DayPropertyType.timePeriod{1}.TimePropertyType.timeRange{0}.TimeRangeType.endTime > 3rdtimeend1
      RENAME_SET_DEFAULT timeInterval{2}.TemporalPropertyType.dayPeriod{0}.DayPropertyType.timePeriod{2}.TimePropertyType.timeRange{0}.TimeRangeType.endTime > 3rdtimeend2
      RENAME_SET_DEFAULT timeInterval{2}.TemporalPropertyType.dayPeriod{0}.DayPropertyType.timePeriod{3}.TimePropertyType.timeRange{0}.TimeRangeType.endTime > 3rdtimeend3
      RENAME_SET_DEFAULT timeInterval{0}.TemporalPropertyType.dateRange{0}.DateRangeType.startDate > 1ststartdate
      RENAME_SET_DEFAULT timeInterval{1}.TemporalPropertyType.dateRange{0}.DateRangeType.startDate > 2ndstartdate
      RENAME_SET_DEFAULT timeInterval{2}.TemporalPropertyType.dateRange{0}.DateRangeType.startDate > 3rdstartdate
      RENAME_SET_DEFAULT timeInterval{0}.TemporalPropertyType.dateRange{0}.DateRangeType.endDate > 1stenddate
      RENAME_SET_DEFAULT timeInterval{1}.TemporalPropertyType.dateRange{0}.DateRangeType.endDate > 2ndenddate
      RENAME_SET_DEFAULT timeInterval{2}.TemporalPropertyType.dateRange{0}.DateRangeType.endDate > 3rdenddate
      RENAME_SET_DEFAULT gml_id > id
      RENAME_SET_DEFAULT fme_basename > chunkname
    -> StringReplacer_4
StringReplacer_4
    CASE = NO
    FIND_TEXT = ([0-9][0-9]:[0-9][0-9]):[0-9][0-9]
    NO_MATCH = _FME_NO_OP_
    REGEXP = YES
    REPLACE_TEXT = \1
    SRC_ATTRS = 2ndtimeend3,3rdtimestart3,2ndtimeend1,1sttimeend2,3rdtimestart2,3rdtimeend3,3rdtimeend2,1sttimeend0,1sttimeend1,3rdtimestart0,2ndtimestart0,3rdtimestart1,2ndtimeend2,2ndtimestart2,1sttimestart0,3rdtimeend0,2ndtimestart3,1sttimestart3,2ndtimeend0,1sttimestart2,1sttimeend3,2ndtimestart1,3rdtimeend1,1sttimestart1
    -> StringReplacer_8
StringReplacer_8
    CASE = NO
    FIND_TEXT = Monday
    NO_MATCH = _FME_NO_OP_
    REGEXP = NO
    REPLACE_TEXT = Mon
    SRC_ATTRS = day204,day101,day002,day004,day105,day201,day203,day100,day104,day202,day206,day103,day003,day102,day000,day200,day205,day106,day001,day005,day006
    -> StringReplacer_9
StringReplacer_9
    CASE = NO
    FIND_TEXT = Tuesday
    NO_MATCH = _FME_NO_OP_
    REGEXP = NO
    REPLACE_TEXT = Tue
    SRC_ATTRS = day204,day101,day002,day004,day105,day201,day203,day100,day104,day202,day206,day103,day003,day102,day000,day200,day205,day106,day001,day005,day006
    -> StringReplacer_13
StringReplacer_13
    CASE = NO
    FIND_TEXT = Wednesday
    NO_MATCH = _FME_NO_OP_
    REGEXP = NO
    REPLACE_TEXT = Wed
    SRC_ATTRS = day006,day000,day105,day101,day203,day003,day103,day200,day001,day204,day201,day104,day002,day106,day205,day206,day102,day202,day004,day005,day100
    -> StringReplacer_23
StringReplacer_23
    CASE = NO
    FIND_TEXT = Thursday
    NO_MATCH = _FME_NO_OP_
    REGEXP = NO
    REPLACE_TEXT = Thu
    SRC_ATTRS = day204,day101,day002,day004,day105,day201,day203,day100,day104,day202,day206,day103,day003,day102,day000,day200,day205,day106,day001,day005,day006
    -> StringReplacer_25
StringReplacer_25
    CASE = NO
    FIND_TEXT = Friday
    NO_MATCH = _FME_NO_OP_
    REGEXP = NO
    REPLACE_TEXT = Fri
    SRC_ATTRS = day204,day101,day002,day004,day105,day201,day203,day100,day104,day202,day206,day103,day003,day102,day000,day200,day205,day106,day001,day005,day006
    -> StringReplacer_32
StringReplacer_32
    CASE = NO
    FIND_TEXT = Saturday
    NO_MATCH = _FME_NO_OP_
    REGEXP = NO
    REPLACE_TEXT = Sat
    SRC_ATTRS = day204,day101,day002,day004,day105,day201,day203,day100,day104,day202,day206,day103,day003,day102,day000,day200,day205,day106,day001,day005,day006
    -> StringReplacer_33
StringReplacer_33
    CASE = NO
    FIND_TEXT = Sunday
    NO_MATCH = _FME_NO_OP_
    REGEXP = NO
    REPLACE_TEXT = Sun
    SRC_ATTRS = day204,day101,day002,day004,day105,day201,day203,day100,day104,day202,day206,day103,day003,day102,day000,day200,day205,day106,day001,day005,day006
    -> SubstringExtractor_15

Bookmark: Format start and end dates
SubstringExtractor_15
    END = 6
    RESULT_ATTR = 1ststartmonth
    SRC_STRING = @Value(1ststartdate)
    START = 5
    -> StringPairReplacer_9
StringPairReplacer_9
    CASE = no
    MAP = 01 Jan 02 Feb 03 Mar 04 Apr 05 May 06 Jun 07 Jul 08 Aug 09 Sep 10 Oct 11 Nov 12 Dec
    RESULT_ATTR = 1ststartmonth
    SRC_ATTR = 1ststartmonth
    -> StringReplacer_6
StringReplacer_6
    CASE = NO
    FIND_TEXT = ^([0-9]*)-([0-9]*)-([0-9]*)
    NO_MATCH = _FME_NO_OP_
    REGEXP = YES
    REPLACE_TEXT = \3 @Value(1ststartmonth) \1
    SRC_ATTRS = 1ststartdate
    -> SubstringExtractor_16
SubstringExtractor_16
    END = 6
    RESULT_ATTR = 1stendmonth
    SRC_STRING = @Value(1stenddate)
    START = 5
    -> StringPairReplacer_10
StringPairReplacer_10
    CASE = no
    MAP = 01 Jan 02 Feb 03 Mar 04 Apr 05 May 06 Jun 07 Jul 08 Aug 09 Sep 10 Oct 11 Nov 12 Dec
    RESULT_ATTR = 1stendmonth
    SRC_ATTR = 1stendmonth
    -> StringReplacer_7
StringReplacer_7
    CASE = NO
    FIND_TEXT = ^([0-9]*)-([0-9]*)-([0-9]*)
    NO_MATCH = _FME_NO_OP_
    REGEXP = YES
    REPLACE_TEXT = \3 @Value(1stendmonth) \1
    SRC_ATTRS = 1stenddate
    -> SubstringExtractor_17
SubstringExtractor_17
    END = 6
    RESULT_ATTR = 2ndstartmonth
    SRC_STRING = @Value(2ndstartdate)
    START = 5
    -> StringPairReplacer_11
StringPairReplacer_11
    CASE = no
    MAP = 01 Jan 02 Feb 03 Mar 04 Apr 05 May 06 Jun 07 Jul 08 Aug 09 Sep 10 Oct 11 Nov 12 Dec
    RESULT_ATTR = 2ndstartmonth
    SRC_ATTR = 2ndstartmonth
    -> StringReplacer_10
StringReplacer_10
    CASE = NO
    FIND_TEXT = ^([0-9]*)-([0-9]*)-([0-9]*)
    NO_MATCH = _FME_NO_OP_
    REGEXP = YES
    REPLACE_TEXT = \3 @Value(2ndstartmonth) \1
    SRC_ATTRS = 2ndstartdate
    -> SubstringExtractor_18
SubstringExtractor_18
    END = 6
    RESULT_ATTR = 2ndendmonth
    SRC_STRING = @Value(2ndenddate)
    START = 5
    -> StringPairReplacer_12
StringPairReplacer_12
    CASE = no
    MAP = 01 Jan 02 Feb 03 Mar 04 Apr 05 May 06 Jun 07 Jul 08 Aug 09 Sep 10 Oct 11 Nov 12 Dec
    RESULT_ATTR = 2ndendmonth
    SRC_ATTR = 2ndendmonth
    -> StringReplacer_11
StringReplacer_11
    CASE = NO
    FIND_TEXT = ^([0-9]*)-([0-9]*)-([0-9]*)
    NO_MATCH = _FME_NO_OP_
    REGEXP = YES
    REPLACE_TEXT = \3 @Value(2ndendmonth) \1
    SRC_ATTRS = 2ndenddate
    -> SubstringExtractor
SubstringExtractor
    END = 6
    RESULT_ATTR = 3rdstartmonth
    SRC_STRING = @Value(3rdstartdate)
    START = 5
    -> StringPairReplacer
StringPairReplacer
    CASE = no
    MAP = 01 Jan 02 Feb 03 Mar 04 Apr 05 May 06 Jun 07 Jul 08 Aug 09 Sep 10 Oct 11 Nov 12 Dec
    RESULT_ATTR = 3rdstartmonth
    SRC_ATTR = 3rdstartmonth
    -> StringReplacer_3
StringReplacer_3
    CASE = NO
    FIND_TEXT = ^([0-9]*)-([0-9]*)-([0-9]*)
    NO_MATCH = _FME_NO_OP_
    REGEXP = YES
    REPLACE_TEXT = \3 @Value(1ststartmonth) \1
    SRC_ATTRS = 3rdstartdate
    -> SubstringExtractor_14
SubstringExtractor_14
    END = 6
    RESULT_ATTR = 3rdendmonth
    SRC_STRING = @Value(3rdenddate)
    START = 5
    -> StringPairReplacer_8
StringPairReplacer_8
    CASE = no
    MAP = 01 Jan 02 Feb 03 Mar 04 Apr 05 May 06 Jun 07 Jul 08 Aug 09 Sep 10 Oct 11 Nov 12 Dec
    RESULT_ATTR = 3rdendmonth
    SRC_ATTR = 3rdendmonth
    -> StringReplacer_5
StringReplacer_5
    CASE = NO
    FIND_TEXT = ^([0-9]*)-([0-9]*)-([0-9]*)
    NO_MATCH = _FME_NO_OP_
    REGEXP = YES
    REPLACE_TEXT = \3 @Value(3rdendmonth) \1
    SRC_ATTRS = 3rdenddate
    -> SubstringExtractor_5

Bookmark: Format day and month expressions
SubstringExtractor_5
    END = 3
    RESULT_ATTR = 1stmonthstart
    SRC_STRING = @Value(monthdaystart0)
    START = 2
    -> SubstringExtractor_6
SubstringExtractor_6
    END = -1
    RESULT_ATTR = 1stdaystart
    SRC_STRING = @Value(monthdaystart0)
    START = -2
    -> SubstringExtractor_7
SubstringExtractor_7
    END = 3
    RESULT_ATTR = 1stmonthend
    SRC_STRING = @Value(monthdayend0)
    START = 2
    -> SubstringExtractor_8
SubstringExtractor_8
    END = -1
    RESULT_ATTR = 1stdayend
    SRC_STRING = @Value(monthdayend0)
    START = -2
    -> StringPairReplacer_3
StringPairReplacer_3
    CASE = no
    MAP = 01 Jan 02 Feb 03 Mar 04 Apr 05 May 06 Jun 07 Jul 08 Aug 09 Sep 10 Oct 11 Nov 12 Dec
    RESULT_ATTR = 1stmonthstart
    SRC_ATTR = 1stmonthstart
    -> StringPairReplacer_4
StringPairReplacer_4
    CASE = no
    MAP = 01 Jan 02 Feb 03 Mar 04 Apr 05 May 06 Jun 07 Jul 08 Aug 09 Sep 10 Oct 11 Nov 12 Dec
    RESULT_ATTR = 1stmonthend
    SRC_ATTR = 1stmonthend
    -> SubstringExtractor_2
SubstringExtractor_2
    END = 3
    RESULT_ATTR = 2ndmonthstart
    SRC_STRING = @Value(monthdaystart1)
    START = 2
    -> SubstringExtractor_3
SubstringExtractor_3
    END = -1
    RESULT_ATTR = 2nddaystart
    SRC_STRING = @Value(monthdaystart1)
    START = -2
    -> SubstringExtractor_4
SubstringExtractor_4
    END = 3
    RESULT_ATTR = 2ndmonthend
    SRC_STRING = @Value(monthdayend1)
    START = 2
    -> SubstringExtractor_9
SubstringExtractor_9
    END = -1
    RESULT_ATTR = 2nddayend
    SRC_STRING = @Value(monthdayend1)
    START = -2
    -> StringPairReplacer_2
StringPairReplacer_2
    CASE = no
    MAP = 01 Jan 02 Feb 03 Mar 04 Apr 05 May 06 Jun 07 Jul 08 Aug 09 Sep 10 Oct 11 Nov 12 Dec
    RESULT_ATTR = 2ndmonthstart
    SRC_ATTR = 2ndmonthstart
    -> StringPairReplacer_5
StringPairReplacer_5
    CASE = no
    MAP = 01 Jan 02 Feb 03 Mar 04 Apr 05 May 06 Jun 07 Jul 08 Aug 09 Sep 10 Oct 11 Nov 12 Dec
    RESULT_ATTR = 2ndmonthend
    SRC_ATTR = 2ndmonthend
    -> SubstringExtractor_10
SubstringExtractor_10
    END = 3
    RESULT_ATTR = 3rdmonthstart
    SRC_STRING = @Value(monthdaystart2)
    START = 2
    -> SubstringExtractor_11
SubstringExtractor_11
    END = -1
    RESULT_ATTR = 3rddaystart
    SRC_STRING = @Value(monthdaystart2)
    START = -2
    -> SubstringExtractor_12
SubstringExtractor_12
    END = 3
    RESULT_ATTR = 3rdmonthend
    SRC_STRING = @Value(monthdayend2)
    START = 2
    -> SubstringExtractor_13
SubstringExtractor_13
    END = -1
    RESULT_ATTR = 3rddayend
    SRC_STRING = @Value(monthdayend2)
    START = -2
    -> StringPairReplacer_6
StringPairReplacer_6
    CASE = no
    MAP = 01 Jan 02 Feb 03 Mar 04 Apr 05 May 06 Jun 07 Jul 08 Aug 09 Sep 10 Oct 11 Nov 12 Dec
    RESULT_ATTR = 3rdmonthstart
    SRC_ATTR = 3rdmonthstart
    -> StringPairReplacer_7
StringPairReplacer_7
    CASE = no
    MAP = 01 Jan 02 Feb 03 Mar 04 Apr 05 May 06 Jun 07 Jul 08 Aug 09 Sep 10 Oct 11 Nov 12 Dec
    RESULT_ATTR = 3rdmonthend
    SRC_ATTR = 3rdmonthend
    -> AttributeCreator_2

Bookmark: Create applicable period 1
AttributeCreator_2
    ATTR_TABLE = SET_TO 1stapplicableperiod = FME_CONDITIONAL:DEFAULT_VALUE''BOOL_OP;AND;COMPOSITE_TEST;<Unused>;TEST @Value(1ststartdate) ATTRIBUTE_HAS_VALUE _FME_BLANK_STRING_;TEST @Value(1stenddate) ATTRIBUTE_HAS_VALUE _FME_BLANK_STRING_'From @Value(1ststartdate) Until @Value(1stenddate)'BOOL_OP;AND;COMPOSITE_TEST;<Unused>;TEST @Value(1ststartdate) ATTRIBUTE_HAS_VALUE _FME_BLANK_STRING_'From @Value(1ststartdate))'BOOL_OP;AND;COMPOSITE_TEST;<Unused>;TEST @Value(1stenddate) ATTRIBUTE_HAS_VALUE _FME_BLANK_STRING_'Until @Value(1stenddate)'FME_NUM_CONDITIONS4___
    -> AttributeCreator_17
AttributeCreator_17
    ATTR_TABLE = SET_TO 1stapplicableperiod = FME_CONDITIONAL:DEFAULT_VALUE''BOOL_OP;AND;COMPOSITE_TEST;<Unused>;TEST @Value(1stapplicableperiod) ATTRIBUTE_HAS_VALUE _FME_BLANK_STRING_;TEST @Value(date002) ATTRIBUTE_HAS_VALUE _FME_BLANK_STRING_'@Value(1stapplicableperiod) - @Value(date000), @Value(date001), @Value(date002)'BOOL_OP;AND;COMPOSITE_TEST;<Unused>;TEST @Value(1stapplicableperiod) ATTRIBUTE_HAS_VALUE _FME_BLANK_STRING_;TEST @Value(date001) ATTRIBUTE_HAS_VALUE _FME_BLANK_STRING_'@Value(1stapplicableperiod) - @Value(date000), @Value(date001)'BOOL_OP;AND;COMPOSITE_TEST;<Unused>;TEST @Value(1stapplicableperiod) ATTRIBUTE_HAS_VALUE _FME_BLANK_STRING_;TEST @Value(date000) ATTRIBUTE_HAS_VALUE _FME_BLANK_STRING_'@Value(1stapplicableperiod) - @Value(date000)'BOOL_OP;AND;COMPOSITE_TEST;<Unused>;TEST @Value(1stapplicableperiod) ATTRIBUTE_HAS_VALUE _FME_BLANK_STRING_'@Value(1stapplicableperiod)'FME_NUM_CONDITIONS5___
    -> AttributeCreator_40
AttributeCreator_40
    ATTR_TABLE = SET_TO 1stapplicableperiod = FME_CONDITIONAL:DEFAULT_VALUE''BOOL_OP;AND;COMPOSITE_TEST;<Unused>;TEST @Value(1stapplicableperiod) ATTRIBUTE_HAS_VALUE _FME_BLANK_STRING_;TEST @Value(1stmonthstart) ATTRIBUTE_HAS_VALUE _FME_BLANK_STRING_'@Value(1stapplicableperiod) - @Value(2nddaystart) @Value(1stmonthstart) To @Value(1stdayend) @Value(1stmonthend)'BOOL_OP;AND;COMPOSITE_TEST;<Unused>;TEST @Value(1stmonthstart) ATTRIBUTE_HAS_VALUE _FME_BLANK_STRING_'@Value(1stdaystart) @Value(1stmonthstart) To @Value(1stdayend) @Value(1stmonthend)'BOOL_OP;AND;COMPOSITE_TEST;<Unused>;TEST @Value(1stapplicableperiod) ATTRIBUTE_HAS_VALUE _FME_BLANK_STRING_'@Value(1stapplicableperiod)'FME_NUM_CONDITIONS4___
    -> AttributeCreator_20
AttributeCreator_20
    ATTR_TABLE = SET_TO 1stnamedperiods = FME_CONDITIONAL:DEFAULT_VALUE'@Value(period000)'BOOL_OP;OR;COMPOSITE_TEST;<Unused>;TEST @Value(period002) ATTRIBUTE_HAS_VALUE _FME_BLANK_STRING_'@Value(period000), @Value(period001), @Value(period002)'BOOL_OP;OR;COMPOSITE_TEST;<Unused>;TEST @Value(period001) ATTRIBUTE_HAS_VALUE _FME_BLANK_STRING_'@Value(period000), @Value(period001)'FME_NUM_CONDITIONS3___
    -> AttributeCreator_19
AttributeCreator_19
    ATTR_TABLE = SET_TO 1stnameddays = FME_CONDITIONAL:DEFAULT_VALUE'@Value(day000)'BOOL_OP;OR;COMPOSITE_TEST;<Unused>;TEST @Value(day006) ATTRIBUTE_HAS_VALUE _FME_BLANK_STRING_'@Value(day000) @Value(day001) @Value(day002) @Value(day003) @Value(day004) @Value(day005) @Value(day006)'BOOL_OP;OR;COMPOSITE_TEST;<Unused>;TEST @Value(day005) ATTRIBUTE_HAS_VALUE _FME_BLANK_STRING_'@Value(day000) @Value(day001) @Value(day002) @Value(day003) @Value(day004) @Value(day005)'BOOL_OP;OR;COMPOSITE_TEST;<Unused>;TEST @Value(day004) ATTRIBUTE_HAS_VALUE _FME_BLANK_STRING_'@Value(day000) @Value(day001) @Value(day002) @Value(day003) @Value(day004)'BOOL_OP;OR;COMPOSITE_TEST;<Unused>;TEST @Value(day003) ATTRIBUTE_HAS_VALUE _FME_BLANK_STRING_'@Value(day000) @Value(day001) @Value(day002) @Value(day003)'BOOL_OP;OR;COMPOSITE_TEST;<Unused>;TEST @Value(day002) ATTRIBUTE_HAS_VALUE _FME_BLANK_STRING_'@Value(day000) @Value(day001) @Value(day002)'BOOL_OP;OR;COMPOSITE_TEST;<Unused>;TEST @Value(day001) ATTRIBUTE_HAS_VALUE _FME_BLANK_STRING_'@Value(day000) @Value(day001)'FME_NUM_CONDITIONS7___
    -> AttributeCreator_33
AttributeCreator_33
    ATTR_TABLE = SET_TO 1stapplicableperiod = FME_CONDITIONAL:DEFAULT_VALUE''BOOL_OP;AND;COMPOSITE_TEST;<Unused>;TEST @Value(1stapplicableperiod) ATTRIBUTE_HAS_VALUE _FME_BLANK_STRING_;TEST @Value(1stnamedperiods) ATTRIBUTE_HAS_VALUE _FME_BLANK_STRING_;TEST @Value(1stnameddays) ATTRIBUTE_HAS_VALUE _FME_BLANK_STRING_'@Value(1stapplicableperiod) - @Value(1stnameddays), @Value(1stnamedperiods)'BOOL_OP;AND;COMPOSITE_TEST;<Unused>;TEST @Value(1stapplicableperiod) ATTRIBUTE_HAS_VALUE _FME_BLANK_STRING_;TEST @Value(1stnamedperiods) ATTRIBUTE_HAS_VALUE _FME_BLANK_STRING_'@Value(1stapplicableperiod) - @Value(1stnamedperiods)'BOOL_OP;AND;COMPOSITE_TEST;<Unused>;TEST @Value(1stapplicableperiod) ATTRIBUTE_HAS_VALUE _FME_BLANK_STRING_;TEST @Value(1stnameddays) ATTRIBUTE_HAS_VALUE _FME_BLANK_STRING_'@Value(1stapplicableperiod) - @Value(1stnameddays)'BOOL_OP;AND;COMPOSITE_TEST;<Unused>;TEST @Value(1stnamedperiods) ATTRIBUTE_HAS_VALUE _FME_BLANK_STRING_;TEST @Value(1stnameddays) ATTRIBUTE_HAS_VALUE _FME_BLANK_STRING_'@Value(1stnameddays), @Value(1stnamedperiods)'BOOL_OP;AND;COMPOSITE_TEST;<Unused>;TEST @Value(1stnamedperiods) ATTRIBUTE_HAS_VALUE _FME_BLANK_STRING_'@Value(1stnamedperiods)'BOOL_OP;AND;COMPOSITE_TEST;<Unused>;TEST @Value(1stnameddays) ATTRIBUTE_HAS_VALUE _FME_BLANK_STRING_'@Value(1stnameddays)'BOOL_OP;AND;COMPOSITE_TEST;<Unused>;TEST @Value(1stapplicableperiod) ATTRIBUTE_HAS_VALUE _FME_BLANK_STRING_'@Value(1stapplicableperiod)'FME_NUM_CONDITIONS8___
    -> AttributeCreator_27
AttributeCreator_27
    ATTR_TABLE = SET_TO 1stnamedtimes = FME_CONDITIONAL:DEFAULT_VALUE'@Value(time000)'BOOL_OP;OR;COMPOSITE_TEST;<Unused>;TEST @Value(time002) ATTRIBUTE_HAS_VALUE _FME_BLANK_STRING_'@Value(time000), @Value(time001), @Value(time002)'BOOL_OP;OR;COMPOSITE_TEST;<Unused>;TEST @Value(time001) ATTRIBUTE_HAS_VALUE _FME_BLANK_STRING_'@Value(time000), @Value(time001)'FME_NUM_CONDITIONS3___
    -> AttributeCreator_46
AttributeCreator_46
    ATTR_TABLE = SET_TO 1sttimerange = FME_CONDITIONAL:DEFAULT_VALUE''BOOL_OP;AND;COMPOSITE_TEST;<Unused>;TEST 1sttimestart3 NOT_ATTRIBUTE_IS_MISSING _FME_BLANK_STRING_;TEST 1sttimeend3 NOT_ATTRIBUTE_IS_MISSING _FME_BLANK_STRING_'@Value(1sttimestart0)-@Value(1sttimeend0) and @Value(1sttimestart1)-@Value(1sttimeend1) and @Value(1sttimestart2)-@Value(1sttimeend2) and @Value(1sttimestart3)-@Value(1sttimeend3)'BOOL_OP;AND;COMPOSITE_TEST;<Unused>;TEST 1sttimestart2 NOT_ATTRIBUTE_IS_MISSING _FME_BLANK_STRING_;TEST 1sttimeend2 NOT_ATTRIBUTE_IS_MISSING _FME_BLANK_STRING_'@Value(1sttimestart0)-@Value(1sttimeend0) and @Value(1sttimestart1)-@Value(1sttimeend1) and @Value(1sttimestart2)-@Value(1sttimeend2)'BOOL_OP;AND;COMPOSITE_TEST;<Unused>;TEST 1sttimestart1 NOT_ATTRIBUTE_IS_MISSING _FME_BLANK_STRING_;TEST 1sttimeend1 NOT_ATTRIBUTE_IS_MISSING _FME_BLANK_STRING_'@Value(1sttimestart0)-@Value(1sttimeend0) and @Value(1sttimestart1)-@Value(1sttimeend1)'BOOL_OP;AND;COMPOSITE_TEST;<Unused>;TEST 1sttimestart0 NOT_ATTRIBUTE_IS_MISSING _FME_BLANK_STRING_;TEST 1sttimeend0 NOT_ATTRIBUTE_IS_MISSING _FME_BLANK_STRING_'@Value(1sttimestart0)-@Value(1sttimeend0)'FME_NUM_CONDITIONS5___
    -> AttributeCreator_34
AttributeCreator_34
    ATTR_TABLE = SET_TO 1stapplicableperiod = FME_CONDITIONAL:DEFAULT_VALUE''BOOL_OP;AND;COMPOSITE_TEST;<Unused>;TEST @Value(1stapplicableperiod) ATTRIBUTE_HAS_VALUE _FME_BLANK_STRING_;TEST @Value(1stnamedtimes) ATTRIBUTE_HAS_VALUE _FME_BLANK_STRING_;TEST @Value(1sttimerange) ATTRIBUTE_HAS_VALUE _FME_BLANK_STRING_'@Value(1stapplicableperiod) @Value(1stnamedtimes) @Value(1sttimerange)'BOOL_OP;AND;COMPOSITE_TEST;<Unused>;TEST @Value(1stapplicableperiod) ATTRIBUTE_HAS_VALUE _FME_BLANK_STRING_;TEST @Value(1stnamedtimes) ATTRIBUTE_HAS_VALUE _FME_BLANK_STRING_'@Value(1stapplicableperiod) @Value(1stnamedtimes)'BOOL_OP;AND;COMPOSITE_TEST;<Unused>;TEST @Value(1stapplicableperiod) ATTRIBUTE_HAS_VALUE _FME_BLANK_STRING_;TEST @Value(1sttimerange) ATTRIBUTE_HAS_VALUE _FME_BLANK_STRING_'@Value(1stapplicableperiod) @Value(1sttimerange)'BOOL_OP;AND;COMPOSITE_TEST;<Unused>;TEST @Value(1stnamedtimes) ATTRIBUTE_HAS_VALUE _FME_BLANK_STRING_;TEST @Value(1sttimerange) ATTRIBUTE_HAS_VALUE _FME_BLANK_STRING_'@Value(1stnamedtimes) @Value(1sttimerange)'BOOL_OP;AND;COMPOSITE_TEST;<Unused>;TEST @Value(1stnamedtimes) ATTRIBUTE_HAS_VALUE _FME_BLANK_STRING_'@Value(1stnamedtimes)'BOOL_OP;AND;COMPOSITE_TEST;<Unused>;TEST @Value(1sttimerange) ATTRIBUTE_HAS_VALUE _FME_BLANK_STRING_'@Value(1sttimerange)'BOOL_OP;AND;COMPOSITE_TEST;<Unused>;TEST @Value(1stapplicableperiod) ATTRIBUTE_HAS_VALUE _FME_BLANK_STRING_'@Value(1stapplicableperiod)'FME_NUM_CONDITIONS8___
    -> AttributeCreator_4

Bookmark: Create applicable period 2
AttributeCreator_4
    ATTR_TABLE = SET_TO 2ndapplicableperiod = FME_CONDITIONAL:DEFAULT_VALUE''BOOL_OP;AND;COMPOSITE_TEST;<Unused>;TEST @Value(2ndstartdate) ATTRIBUTE_HAS_VALUE _FME_BLANK_STRING_;TEST @Value(2ndenddate) ATTRIBUTE_HAS_VALUE _FME_BLANK_STRING_'From @Value(2ndstartdate) Until @Value(2ndenddate)'BOOL_OP;AND;COMPOSITE_TEST;<Unused>;TEST @Value(2ndstartdate) ATTRIBUTE_HAS_VALUE _FME_BLANK_STRING_'From @Value(2ndstartdate))'BOOL_OP;AND;COMPOSITE_TEST;<Unused>;TEST @Value(2ndenddate) ATTRIBUTE_HAS_VALUE _FME_BLANK_STRING_'Until @Value(2ndenddate)'FME_NUM_CONDITIONS4___
    -> AttributeCreator_3
AttributeCreator_3
    ATTR_TABLE = SET_TO 2ndapplicableperiod = FME_CONDITIONAL:DEFAULT_VALUE''BOOL_OP;AND;COMPOSITE_TEST;<Unused>;TEST @Value(2ndapplicableperiod) ATTRIBUTE_HAS_VALUE _FME_BLANK_STRING_;TEST @Value(date102) ATTRIBUTE_HAS_VALUE _FME_BLANK_STRING_'@Value(2ndapplicableperiod) - @Value(date100), @Value(date101), @Value(date102)'BOOL_OP;AND;COMPOSITE_TEST;<Unused>;TEST @Value(2ndapplicableperiod) ATTRIBUTE_HAS_VALUE _FME_BLANK_STRING_;TEST @Value(date101) ATTRIBUTE_HAS_VALUE _FME_BLANK_STRING_'@Value(2ndapplicableperiod) - @Value(date100), @Value(date101)'BOOL_OP;AND;COMPOSITE_TEST;<Unused>;TEST @Value(2ndapplicableperiod) ATTRIBUTE_HAS_VALUE _FME_BLANK_STRING_;TEST @Value(date100) ATTRIBUTE_HAS_VALUE _FME_BLANK_STRING_'@Value(2ndapplicableperiod) - @Value(date100)'BOOL_OP;AND;COMPOSITE_TEST;<Unused>;TEST @Value(2ndapplicableperiod) ATTRIBUTE_HAS_VALUE _FME_BLANK_STRING_'@Value(2ndapplicableperiod)'FME_NUM_CONDITIONS5___
    -> AttributeCreator_9
AttributeCreator_9
    ATTR_TABLE = SET_TO 2ndapplicableperiod = FME_CONDITIONAL:DEFAULT_VALUE''BOOL_OP;AND;COMPOSITE_TEST;<Unused>;TEST @Value(2ndapplicableperiod) ATTRIBUTE_HAS_VALUE _FME_BLANK_STRING_;TEST @Value(2ndmonthstart) ATTRIBUTE_HAS_VALUE _FME_BLANK_STRING_'@Value(2ndapplicableperiod) - @Value(2nddaystart) @Value(2ndmonthstart) To @Value(2nddayend) @Value(2ndmonthend)'BOOL_OP;AND;COMPOSITE_TEST;<Unused>;TEST @Value(2ndmonthstart) ATTRIBUTE_HAS_VALUE _FME_BLANK_STRING_'@Value(2nddaystart) @Value(2ndmonthstart) To @Value(2nddayend) @Value(2ndmonthend)'BOOL_OP;AND;COMPOSITE_TEST;<Unused>;TEST @Value(2ndapplicableperiod) ATTRIBUTE_HAS_VALUE _FME_BLANK_STRING_'@Value(2ndapplicableperiod)'FME_NUM_CONDITIONS4___
    -> AttributeCreator_25
AttributeCreator_25
    ATTR_TABLE = SET_TO 2ndnamedperiods = FME_CONDITIONAL:DEFAULT_VALUE'@Value(period100)'BOOL_OP;OR;COMPOSITE_TEST;<Unused>;TEST @Value(period102) ATTRIBUTE_HAS_VALUE _FME_BLANK_STRING_'@Value(period100), @Value(period101), @Value(period102)'BOOL_OP;OR;COMPOSITE_TEST;<Unused>;TEST @Value(period101) ATTRIBUTE_HAS_VALUE _FME_BLANK_STRING_'@Value(period100), @Value(period101)'FME_NUM_CONDITIONS3___
    -> AttributeCreator_23
AttributeCreator_23
    ATTR_TABLE = SET_TO 2ndnameddays = FME_CONDITIONAL:DEFAULT_VALUE'@Value(day100)'BOOL_OP;OR;COMPOSITE_TEST;<Unused>;TEST @Value(day106) ATTRIBUTE_HAS_VALUE _FME_BLANK_STRING_'@Value(day100) @Value(day101) @Value(day102) @Value(day103) @Value(day104) @Value(day105) @Value(day106)'BOOL_OP;OR;COMPOSITE_TEST;<Unused>;TEST @Value(day105) ATTRIBUTE_HAS_VALUE _FME_BLANK_STRING_'@Value(day100) @Value(day101) @Value(day102) @Value(day103) @Value(day104) @Value(day105)'BOOL_OP;OR;COMPOSITE_TEST;<Unused>;TEST @Value(day104) ATTRIBUTE_HAS_VALUE _FME_BLANK_STRING_'@Value(day100) @Value(day101) @Value(day102) @Value(day103) @Value(day104)'BOOL_OP;OR;COMPOSITE_TEST;<Unused>;TEST @Value(day103) ATTRIBUTE_HAS_VALUE _FME_BLANK_STRING_'@Value(day100) @Value(day101) @Value(day102) @Value(day103)'BOOL_OP;OR;COMPOSITE_TEST;<Unused>;TEST @Value(day102) ATTRIBUTE_HAS_VALUE _FME_BLANK_STRING_'@Value(day100) @Value(day101) @Value(day102)'BOOL_OP;OR;COMPOSITE_TEST;<Unused>;TEST @Value(day101) ATTRIBUTE_HAS_VALUE _FME_BLANK_STRING_'@Value(day100) @Value(day101)'FME_NUM_CONDITIONS7___
    -> AttributeCreator_24
AttributeCreator_24
    ATTR_TABLE = SET_TO 2ndapplicableperiod = FME_CONDITIONAL:DEFAULT_VALUE''BOOL_OP;AND;COMPOSITE_TEST;<Unused>;TEST @Value(2ndapplicableperiod) ATTRIBUTE_HAS_VALUE _FME_BLANK_STRING_;TEST @Value(2ndnamedperiods) ATTRIBUTE_HAS_VALUE _FME_BLANK_STRING_;TEST @Value(2ndnameddays) ATTRIBUTE_HAS_VALUE _FME_BLANK_STRING_'@Value(2ndapplicableperiod) - @Value(2ndnameddays), @Value(2ndnamedperiods)'BOOL_OP;AND;COMPOSITE_TEST;<Unused>;TEST @Value(2ndapplicableperiod) ATTRIBUTE_HAS_VALUE _FME_BLANK_STRING_;TEST @Value(2ndnamedperiods) ATTRIBUTE_HAS_VALUE _FME_BLANK_STRING_'@Value(2ndapplicableperiod) - @Value(2ndnamedperiods)'BOOL_OP;AND;COMPOSITE_TEST;<Unused>;TEST @Value(2ndapplicableperiod) ATTRIBUTE_HAS_VALUE _FME_BLANK_STRING_;TEST @Value(2ndnameddays) ATTRIBUTE_HAS_VALUE _FME_BLANK_STRING_'@Value(2ndapplicableperiod) - @Value(2ndnameddays)'BOOL_OP;AND;COMPOSITE_TEST;<Unused>;TEST @Value(2ndnamedperiods) ATTRIBUTE_HAS_VALUE _FME_BLANK_STRING_;TEST @Value(2ndnameddays) ATTRIBUTE_HAS_VALUE _FME_BLANK_STRING_'@Value(2ndnameddays), @Value(2ndnamedperiods)'BOOL_OP;AND;COMPOSITE_TEST;<Unused>;TEST @Value(2ndnamedperiods) ATTRIBUTE_HAS_VALUE _FME_BLANK_STRING_'@Value(2ndnamedperiods)'BOOL_OP;AND;COMPOSITE_TEST;<Unused>;TEST @Value(2ndnameddays) ATTRIBUTE_HAS_VALUE _FME_BLANK_STRING_'@Value(2ndnameddays)'BOOL_OP;AND;COMPOSITE_TEST;<Unused>;TEST @Value(2ndapplicableperiod) ATTRIBUTE_HAS_VALUE _FME_BLANK_STRING_'@Value(2ndapplicableperiod)'FME_NUM_CONDITIONS8___
    -> AttributeCreator_28
AttributeCreator_28
    ATTR_TABLE = SET_TO 2ndnamedtimes = FME_CONDITIONAL:DEFAULT_VALUE'@Value(time100)'BOOL_OP;OR;COMPOSITE_TEST;<Unused>;TEST @Value(time102) ATTRIBUTE_HAS_VALUE _FME_BLANK_STRING_'@Value(time100), @Value(time101), @Value(time102)'BOOL_OP;OR;COMPOSITE_TEST;<Unused>;TEST @Value(time101) ATTRIBUTE_HAS_VALUE _FME_BLANK_STRING_'@Value(time100), @Value(time101)'FME_NUM_CONDITIONS3___
    -> AttributeCreator_43
AttributeCreator_43
    ATTR_TABLE = SET_TO 2ndtimerange = FME_CONDITIONAL:DEFAULT_VALUE''BOOL_OP;AND;COMPOSITE_TEST;<Unused>;TEST 2ndtimestart3 NOT_ATTRIBUTE_IS_MISSING _FME_BLANK_STRING_;TEST 2ndtimeend3 NOT_ATTRIBUTE_IS_MISSING _FME_BLANK_STRING_'@Value(2ndtimestart0)-@Value(2ndtimeend0) and @Value(2ndtimestart1)-@Value(2ndtimeend1) and @Value(2ndtimestart2)-@Value(2ndtimeend2) and @Value(2ndtimestart3)-@Value(2ndtimeend3)'BOOL_OP;AND;COMPOSITE_TEST;<Unused>;TEST 2ndtimestart2 NOT_ATTRIBUTE_IS_MISSING _FME_BLANK_STRING_;TEST 2ndtimeend2 NOT_ATTRIBUTE_IS_MISSING _FME_BLANK_STRING_'@Value(2ndtimestart0)-@Value(2ndtimeend0) and @Value(2ndtimestart1)-@Value(2ndtimeend1) and @Value(2ndtimestart2)-@Value(2ndtimeend2)'BOOL_OP;AND;COMPOSITE_TEST;<Unused>;TEST 2ndtimestart1 NOT_ATTRIBUTE_IS_MISSING _FME_BLANK_STRING_;TEST 2ndtimeend1 NOT_ATTRIBUTE_IS_MISSING _FME_BLANK_STRING_'@Value(2ndtimestart0)-@Value(2ndtimeend0) and @Value(2ndtimestart1)-@Value(2ndtimeend1)'BOOL_OP;AND;COMPOSITE_TEST;<Unused>;TEST 2ndtimestart0 NOT_ATTRIBUTE_IS_MISSING _FME_BLANK_STRING_;TEST 2ndtimeend0 NOT_ATTRIBUTE_IS_MISSING _FME_BLANK_STRING_'@Value(2ndtimestart0)-@Value(2ndtimeend0)'FME_NUM_CONDITIONS5___
    -> AttributeCreator_26
AttributeCreator_26
    ATTR_TABLE = SET_TO 2ndapplicableperiod = FME_CONDITIONAL:DEFAULT_VALUE''BOOL_OP;AND;COMPOSITE_TEST;<Unused>;TEST @Value(2ndapplicableperiod) ATTRIBUTE_HAS_VALUE _FME_BLANK_STRING_;TEST @Value(2ndnamedtimes) ATTRIBUTE_HAS_VALUE _FME_BLANK_STRING_;TEST @Value(2ndtimerange) ATTRIBUTE_HAS_VALUE _FME_BLANK_STRING_'@Value(2ndapplicableperiod) @Value(2ndnamedtimes) @Value(2ndtimerange)'BOOL_OP;AND;COMPOSITE_TEST;<Unused>;TEST @Value(2ndapplicableperiod) ATTRIBUTE_HAS_VALUE _FME_BLANK_STRING_;TEST @Value(2ndnamedtimes) ATTRIBUTE_HAS_VALUE _FME_BLANK_STRING_'@Value(2ndapplicableperiod) @Value(2ndnamedtimes)'BOOL_OP;AND;COMPOSITE_TEST;<Unused>;TEST @Value(2ndapplicableperiod) ATTRIBUTE_HAS_VALUE _FME_BLANK_STRING_;TEST @Value(2ndtimerange) ATTRIBUTE_HAS_VALUE _FME_BLANK_STRING_'@Value(2ndapplicableperiod) @Value(2ndtimerange)'BOOL_OP;AND;COMPOSITE_TEST;<Unused>;TEST @Value(2ndnamedtimes) ATTRIBUTE_HAS_VALUE _FME_BLANK_STRING_;TEST @Value(2ndtimerange) ATTRIBUTE_HAS_VALUE _FME_BLANK_STRING_'@Value(2ndnamedtimes) @Value(2ndtimerange)'BOOL_OP;AND;COMPOSITE_TEST;<Unused>;TEST @Value(2ndnamedtimes) ATTRIBUTE_HAS_VALUE _FME_BLANK_STRING_'@Value(2ndnamedtimes)'BOOL_OP;AND;COMPOSITE_TEST;<Unused>;TEST @Value(2ndtimerange) ATTRIBUTE_HAS_VALUE _FME_BLANK_STRING_'@Value(2ndtimerange)'BOOL_OP;AND;COMPOSITE_TEST;<Unused>;TEST @Value(2ndapplicableperiod) ATTRIBUTE_HAS_VALUE _FME_BLANK_STRING_'@Value(2ndapplicableperiod)'FME_NUM_CONDITIONS8___
    -> AttributeCreator_6

Bookmark: Create applicable period 3
AttributeCreator_6
    ATTR_TABLE = SET_TO 3rdapplicableperiod = FME_CONDITIONAL:DEFAULT_VALUE''BOOL_OP;AND;COMPOSITE_TEST;<Unused>;TEST @Value(3rdstartdate) ATTRIBUTE_HAS_VALUE _FME_BLANK_STRING_;TEST @Value(3rdenddate) ATTRIBUTE_HAS_VALUE _FME_BLANK_STRING_'From @Value(3rdstartdate) Until @Value(3rdenddate)'BOOL_OP;AND;COMPOSITE_TEST;<Unused>;TEST @Value(3rdstartdate) ATTRIBUTE_HAS_VALUE _FME_BLANK_STRING_'From @Value(3rdstartdate))'BOOL_OP;AND;COMPOSITE_TEST;<Unused>;TEST @Value(3rdenddate) ATTRIBUTE_HAS_VALUE _FME_BLANK_STRING_'Until @Value(3rdenddate)'FME_NUM_CONDITIONS4___
    -> AttributeCreator_5
AttributeCreator_5
    ATTR_TABLE = SET_TO 3rdapplicableperiod = FME_CONDITIONAL:DEFAULT_VALUE''BOOL_OP;AND;COMPOSITE_TEST;<Unused>;TEST @Value(3rdapplicableperiod) ATTRIBUTE_HAS_VALUE _FME_BLANK_STRING_;TEST @Value(date202) ATTRIBUTE_HAS_VALUE _FME_BLANK_STRING_'@Value(3rdapplicableperiod) - @Value(date200), @Value(date201), @Value(date202)'BOOL_OP;AND;COMPOSITE_TEST;<Unused>;TEST @Value(3rdapplicableperiod) ATTRIBUTE_HAS_VALUE _FME_BLANK_STRING_;TEST @Value(date201) ATTRIBUTE_HAS_VALUE _FME_BLANK_STRING_'@Value(3rdapplicableperiod) - @Value(date200), @Value(date201)'BOOL_OP;AND;COMPOSITE_TEST;<Unused>;TEST @Value(3rdapplicableperiod) ATTRIBUTE_HAS_VALUE _FME_BLANK_STRING_;TEST @Value(date200) ATTRIBUTE_HAS_VALUE _FME_BLANK_STRING_'@Value(3rdapplicableperiod) - @Value(date200)'BOOL_OP;AND;COMPOSITE_TEST;<Unused>;TEST @Value(3rdapplicableperiod) ATTRIBUTE_HAS_VALUE _FME_BLANK_STRING_'@Value(3rdapplicableperiod)'FME_NUM_CONDITIONS5___
    -> AttributeCreator_8
AttributeCreator_8
    ATTR_TABLE = SET_TO 3rdapplicableperiod = FME_CONDITIONAL:DEFAULT_VALUE''BOOL_OP;AND;COMPOSITE_TEST;<Unused>;TEST @Value(3rdapplicableperiod) ATTRIBUTE_HAS_VALUE _FME_BLANK_STRING_;TEST @Value(3rdmonthstart) ATTRIBUTE_HAS_VALUE _FME_BLANK_STRING_'@Value(3rdapplicableperiod) - @Value(3rddaystart) @Value(3rdmonthstart) To @Value(3rddayend) @Value(3rdmonthend)'BOOL_OP;AND;COMPOSITE_TEST;<Unused>;TEST @Value(3rdmonthstart) ATTRIBUTE_HAS_VALUE _FME_BLANK_STRING_'@Value(3rddaystart) @Value(3rdmonthstart) To @Value(3rddayend) @Value(3rdmonthend)'BOOL_OP;AND;COMPOSITE_TEST;<Unused>;TEST @Value(3rdapplicableperiod) ATTRIBUTE_HAS_VALUE _FME_BLANK_STRING_'@Value(3rdapplicableperiod)'FME_NUM_CONDITIONS4___
    -> AttributeCreator_36
AttributeCreator_36
    ATTR_TABLE = SET_TO 3rdnamedperiods = FME_CONDITIONAL:DEFAULT_VALUE'@Value(period200)'BOOL_OP;OR;COMPOSITE_TEST;<Unused>;TEST @Value(period202) ATTRIBUTE_HAS_VALUE _FME_BLANK_STRING_'@Value(period200), @Value(period201), @Value(period202)'BOOL_OP;OR;COMPOSITE_TEST;<Unused>;TEST @Value(period201) ATTRIBUTE_HAS_VALUE _FME_BLANK_STRING_'@Value(period200), @Value(period201)'FME_NUM_CONDITIONS3___
    -> AttributeCreator_31
AttributeCreator_31
    ATTR_TABLE = SET_TO 3rdnameddays = FME_CONDITIONAL:DEFAULT_VALUE'@Value(day200)'BOOL_OP;OR;COMPOSITE_TEST;<Unused>;TEST @Value(day206) ATTRIBUTE_HAS_VALUE _FME_BLANK_STRING_'@Value(day200) @Value(day201) @Value(day202) @Value(day203) @Value(day204) @Value(day205) @Value(day206)'BOOL_OP;OR;COMPOSITE_TEST;<Unused>;TEST @Value(day205) ATTRIBUTE_HAS_VALUE _FME_BLANK_STRING_'@Value(day200) @Value(day201) @Value(day202) @Value(day203) @Value(day204) @Value(day205)'BOOL_OP;OR;COMPOSITE_TEST;<Unused>;TEST @Value(day204) ATTRIBUTE_HAS_VALUE _FME_BLANK_STRING_'@Value(day200) @Value(day201) @Value(day202) @Value(day203) @Value(day204)'BOOL_OP;OR;COMPOSITE_TEST;<Unused>;TEST @Value(day203) ATTRIBUTE_HAS_VALUE _FME_BLANK_STRING_'@Value(day200) @Value(day201) @Value(day202) @Value(day203)'BOOL_OP;OR;COMPOSITE_TEST;<Unused>;TEST @Value(day202) ATTRIBUTE_HAS_VALUE _FME_BLANK_STRING_'@Value(day200) @Value(day201) @Value(day202)'BOOL_OP;OR;COMPOSITE_TEST;<Unused>;TEST @Value(day201) ATTRIBUTE_HAS_VALUE _FME_BLANK_STRING_'@Value(day200) @Value(day201)'FME_NUM_CONDITIONS7___
    -> AttributeCreator_35
AttributeCreator_35
    ATTR_TABLE = SET_TO 3rdapplicableperiod = FME_CONDITIONAL:DEFAULT_VALUE''BOOL_OP;AND;COMPOSITE_TEST;<Unused>;TEST @Value(3rdapplicableperiod) ATTRIBUTE_HAS_VALUE _FME_BLANK_STRING_;TEST @Value(3rdnamedperiods) ATTRIBUTE_HAS_VALUE _FME_BLANK_STRING_;TEST @Value(3rdnameddays) ATTRIBUTE_HAS_VALUE _FME_BLANK_STRING_'@Value(3rdapplicableperiod) - @Value(3rdnameddays), @Value(3rdnamedperiods)'BOOL_OP;AND;COMPOSITE_TEST;<Unused>;TEST @Value(3rdapplicableperiod) ATTRIBUTE_HAS_VALUE _FME_BLANK_STRING_;TEST @Value(3rdnamedperiods) ATTRIBUTE_HAS_VALUE _FME_BLANK_STRING_'@Value(3rdapplicableperiod) - @Value(3rdnamedperiods)'BOOL_OP;AND;COMPOSITE_TEST;<Unused>;TEST @Value(3rdapplicableperiod) ATTRIBUTE_HAS_VALUE _FME_BLANK_STRING_;TEST @Value(3rdnameddays) ATTRIBUTE_HAS_VALUE _FME_BLANK_STRING_'@Value(3rdapplicableperiod) - @Value(3rdnameddays)'BOOL_OP;AND;COMPOSITE_TEST;<Unused>;TEST @Value(3rdnamedperiods) ATTRIBUTE_HAS_VALUE _FME_BLANK_STRING_;TEST @Value(3rdnameddays) ATTRIBUTE_HAS_VALUE _FME_BLANK_STRING_'@Value(3rdnameddays), @Value(3rdnamedperiods)'BOOL_OP;AND;COMPOSITE_TEST;<Unused>;TEST @Value(3rdnamedperiods) ATTRIBUTE_HAS_VALUE _FME_BLANK_STRING_'@Value(3rdnamedperiods)'BOOL_OP;AND;COMPOSITE_TEST;<Unused>;TEST @Value(3rdnameddays) ATTRIBUTE_HAS_VALUE _FME_BLANK_STRING_'@Value(3rdnameddays)'BOOL_OP;AND;COMPOSITE_TEST;<Unused>;TEST @Value(3rdapplicableperiod) ATTRIBUTE_HAS_VALUE _FME_BLANK_STRING_'@Value(3rdapplicableperiod)'FME_NUM_CONDITIONS8___
    -> AttributeCreator_38
AttributeCreator_38
    ATTR_TABLE = SET_TO 3rdnamedtimes = FME_CONDITIONAL:DEFAULT_VALUE'@Value(time200)'BOOL_OP;OR;COMPOSITE_TEST;<Unused>;TEST @Value(time202) ATTRIBUTE_HAS_VALUE _FME_BLANK_STRING_'@Value(time200), @Value(time201), @Value(time202)'BOOL_OP;OR;COMPOSITE_TEST;<Unused>;TEST @Value(time201) ATTRIBUTE_HAS_VALUE _FME_BLANK_STRING_'@Value(time200), @Value(time201)'FME_NUM_CONDITIONS3___
    -> AttributeCreator_44
AttributeCreator_44
    ATTR_TABLE = SET_TO 3rdtimerange = FME_CONDITIONAL:DEFAULT_VALUE''BOOL_OP;AND;COMPOSITE_TEST;<Unused>;TEST 3rdtimestart3 NOT_ATTRIBUTE_IS_MISSING _FME_BLANK_STRING_;TEST 3rdtimeend3 NOT_ATTRIBUTE_IS_MISSING _FME_BLANK_STRING_'@Value(3rdtimestart0)-@Value(3rdtimeend0) and @Value(3rdtimestart1)-@Value(3rdtimeend1) and @Value(3rdtimestart2)-@Value(3rdtimeend2) and @Value(3rdtimestart3)-@Value(3rdtimeend3)'BOOL_OP;AND;COMPOSITE_TEST;<Unused>;TEST 3rdtimestart2 NOT_ATTRIBUTE_IS_MISSING _FME_BLANK_STRING_;TEST 3rdtimeend2 NOT_ATTRIBUTE_IS_MISSING _FME_BLANK_STRING_'@Value(3rdtimestart0)-@Value(3rdtimeend0) and @Value(3rdtimestart1)-@Value(3rdtimeend1) and @Value(3rdtimestart2)-@Value(3rdtimeend2)'BOOL_OP;AND;COMPOSITE_TEST;<Unused>;TEST 3rdtimestart1 NOT_ATTRIBUTE_IS_MISSING _FME_BLANK_STRING_;TEST 3rdtimeend1 NOT_ATTRIBUTE_IS_MISSING _FME_BLANK_STRING_'@Value(3rdtimestart0)-@Value(3rdtimeend0) and @Value(3rdtimestart1)-@Value(3rdtimeend1)'BOOL_OP;AND;COMPOSITE_TEST;<Unused>;TEST 3rdtimestart0 NOT_ATTRIBUTE_IS_MISSING _FME_BLANK_STRING_;TEST 3rdtimeend0 NOT_ATTRIBUTE_IS_MISSING _FME_BLANK_STRING_'@Value(3rdtimestart0)-@Value(3rdtimeend0)'FME_NUM_CONDITIONS5___
    -> AttributeCreator_37
AttributeCreator_37
    ATTR_TABLE = SET_TO 3rdapplicableperiod = FME_CONDITIONAL:DEFAULT_VALUE''BOOL_OP;AND;COMPOSITE_TEST;<Unused>;TEST @Value(3rdapplicableperiod) ATTRIBUTE_HAS_VALUE _FME_BLANK_STRING_;TEST @Value(3rdnamedtimes) ATTRIBUTE_HAS_VALUE _FME_BLANK_STRING_;TEST @Value(3rdtimerange) ATTRIBUTE_HAS_VALUE _FME_BLANK_STRING_'@Value(3rdapplicableperiod) @Value(3rdnamedtimes) @Value(3rdtimerange)'BOOL_OP;AND;COMPOSITE_TEST;<Unused>;TEST @Value(3rdapplicableperiod) ATTRIBUTE_HAS_VALUE _FME_BLANK_STRING_;TEST @Value(3rdnamedtimes) ATTRIBUTE_HAS_VALUE _FME_BLANK_STRING_'@Value(3rdapplicableperiod) @Value(3rdnamedtimes)'BOOL_OP;AND;COMPOSITE_TEST;<Unused>;TEST @Value(3rdapplicableperiod) ATTRIBUTE_HAS_VALUE _FME_BLANK_STRING_;TEST @Value(3rdtimerange) ATTRIBUTE_HAS_VALUE _FME_BLANK_STRING_'@Value(3rdapplicableperiod) @Value(3rdtimerange)'BOOL_OP;AND;COMPOSITE_TEST;<Unused>;TEST @Value(3rdnamedtimes) ATTRIBUTE_HAS_VALUE _FME_BLANK_STRING_;TEST @Value(3rdtimerange) ATTRIBUTE_HAS_VALUE _FME_BLANK_STRING_'@Value(3rdnamedtimes) @Value(3rdtimerange)'BOOL_OP;OR;COMPOSITE_TEST;<Unused>;TEST @Value(3rdnamedtimes) ATTRIBUTE_HAS_VALUE _FME_BLANK_STRING_'@Value(3rdnamedtimes)'BOOL_OP;OR;COMPOSITE_TEST;<Unused>;TEST @Value(3rdtimerange) ATTRIBUTE_HAS_VALUE _FME_BLANK_STRING_'@Value(3rdtimerange)'BOOL_OP;OR;COMPOSITE_TEST;<Unused>;TEST @Value(3rdapplicableperiod) ATTRIBUTE_HAS_VALUE _FME_BLANK_STRING_'@Value(3rdapplicableperiod)'FME_NUM_CONDITIONS8___
    -> AttributeCreator_32

Bookmark: Consolidate applicable period
AttributeCreator_32
    ATTR_TABLE = SET_TO ApplicablePeriod = FME_CONDITIONAL:DEFAULT_VALUE'@Value(1stapplicableperiod)'BOOL_OP;AND;COMPOSITE_TEST;<Unused>;TEST @Value(3rdapplicableperiod) ATTRIBUTE_HAS_VALUE _FME_BLANK_STRING_;TEST @Value(3rdapplicableperiod) != @Value(2ndapplicableperiod);TEST @Value(3rdapplicableperiod) != @Value(1stapplicableperiod)'@Value(1stapplicableperiod) | @Value(2ndapplicableperiod) | @Value(3rdapplicableperiod)'BOOL_OP;AND;COMPOSITE_TEST;<Unused>;TEST @Value(2ndapplicableperiod) ATTRIBUTE_HAS_VALUE _FME_BLANK_STRING_;TEST @Value(2ndapplicableperiod) != @Value(1stapplicableperiod)'@Value(1stapplicableperiod) | @Value(2ndapplicableperiod)'FME_NUM_CONDITIONS3___
    -> AttributeKeeper_5
AttributeKeeper_5
    KEEP_ATTRS = ApplicablePeriod,worksProhibited,nationalCycleRoute,obstruction,publicRightOfWay,id,reasonForChange,dedication,identifier,validFrom,planningOrder,chunkname,quietRoute,beginLifespanVersion
    -> StringReplacer_2
StringReplacer_2
    CASE = NO
    FIND_TEXT = " 00:00-00:00"
    NO_MATCH = _FME_NO_OP_
    REGEXP = NO
    SRC_ATTRS = ApplicablePeriod
    -> HighwayDedication (writer GEOPACKAGE_1)
HighwayDedication (writer GEOPACKAGE_1)
    attributes: id text(25), identifier text(37), dedication text(35), publicRightOfWay boolean, nationalCycleRoute boolean, quietRoute boolean, obstruction boolean, planningOrder boolean, worksProhibited boolean, ApplicablePeriod text(180), beginLifespanVersion text(20), reasonForChange text(32), validFrom text(20), chunkname text(50)

Bookmark: Network_Reference
ListExploder
    ATTR_ACCUM_MODE = Merge List Attributes
    ATTR_CONFLICT_RES = Use List Attribute Values
    INDEX_ATTR = _element_index
    LIST_ATTR = networkRef{}
    ELEMENTS -> AttributeKeeper
AttributeKeeper
    KEEP_ATTRS = NetworkReference.element.xlink_href,gml_id
    -> AttributeTrimmer
Note: Remove # to enable table joins
AttributeTrimmer
    SRC_ATTRS = NetworkReference.element.xlink_href
    TRIM_CHARS = #
    TRIM_TO_NONE = Yes
    TRIM_TYPE = Left
    -> Network_Reference (writer GEOPACKAGE_1)

Bookmark: Time qualifiers
ListExploder_8
    ATTR_ACCUM_MODE = Merge Incoming List
    ATTR_CONFLICT_RES = Use Original
    INDEX_ATTR = _element_index
    LIST_ATTR = timeInterval{}
    LIST_FOUND -> AttributeRenamer_17
AttributeRenamer_17
    ATTR_TABLE = RENAME_SET_DEFAULT gml_id > parentFeature_ID
    -> Counter
Note: Creates an identifier for date element
Counter
    CNT_ATTR = timeInterval_ID
    DOMAIN = counter
    SCOPE = Global
    START = 0
    -> ListExploder_9
    -> TQ_Parent_Date_Join (writer GEOPACKAGE_1)
    -> ListExploder_10
    -> ListExploder_11
ListExploder_11
    ATTR_ACCUM_MODE = Merge Incoming List
    ATTR_CONFLICT_RES = Use Original
    INDEX_ATTR = _element_index
    LIST_ATTR = TemporalPropertyType.dayPeriod{}
    LIST_FOUND -> Counter_2
Note: Creates an identifier for day element
Counter_2
    CNT_ATTR = dayPeriod_ID
    DOMAIN = counter
    SCOPE = Global
    START = 0
    -> ListExploder_12
    -> ListExploder_13
    -> ListExploder_14
    -> TQ_Date_Day_Join (writer GEOPACKAGE_1)
Note: Some transformers are incomplete as the data is not currently present
ListExploder_14
    ATTR_ACCUM_MODE = Merge Incoming List
    ATTR_CONFLICT_RES = Use Original
    INDEX_ATTR = _element_index
    LIST_ATTR = DayPropertyType.timePeriod{}
    LIST_FOUND -> Counter_3
Note: Creates an identifier for time element
Counter_3
    CNT_ATTR = timePeriod_ID
    DOMAIN = counter
    SCOPE = Global
    START = 0
    -> ListExploder_15
    -> ListExploder_16
    -> TQ_Day_Time_Join (writer GEOPACKAGE_1)

Bookmark: Date element
TQ_Parent_Date_Join (writer GEOPACKAGE_1)
    attributes: parentFeature_ID text(50), timeInterval_ID mediumint

Bookmark: DateRange
ListExploder_9
    ATTR_ACCUM_MODE = Merge Incoming List
    ATTR_CONFLICT_RES = Use Original
    INDEX_ATTR = _element_index
    LIST_ATTR = TemporalPropertyType.dateRange{}
    LIST_FOUND -> AttributeRenamer_6
AttributeRenamer_6
    ATTR_LIST = DateRangeType.startDate,startDate,,DateRangeType.endDate,endDate,,DateRangeType.startMonthDay,startMonthDay,,DateRangeType.endMonthDay,endMonthDay,
    -> DateFormatter_3
DateFormatter_3
    DATE_ATTR = endDate,startDate
    FMT = FME Date (%Y%m%d)
    INVALID_DATE_VALUE = _FME_NO_OP_
    SRCFMT = Unknown - Automatic Detection
    -> TQ_DateRange (writer GEOPACKAGE_1)
TQ_DateRange (writer GEOPACKAGE_1)
    attributes: parentFeature_ID text(50), timeInterval_ID mediumint, startDate text(20), endDate text(20), startMonthDay text(10), endMonthDay text(10)

Bookmark: NamedDate
ListExploder_10
    ATTR_ACCUM_MODE = Merge Incoming List
    ATTR_CONFLICT_RES = Use Original
    INDEX_ATTR = _element_index
    LIST_ATTR = TemporalPropertyType.namedDate{}
    LIST_FOUND -> AttributeRenamer_12
AttributeRenamer_12
    ATTR_LIST = TemporalPropertyType.namedDate,namedDate,
    -> TQ_NamedDate (writer GEOPACKAGE_1)
TQ_NamedDate (writer GEOPACKAGE_1)
    attributes: parentFeature_ID text(50), timeInterval_ID mediumint, namedDate text(20)

Bookmark: Day element
TQ_Date_Day_Join (writer GEOPACKAGE_1)
    attributes: parentFeature_ID text(50), timeInterval_ID mediumint, dayPeriod_ID mediumint

Bookmark: NamedDay
ListExploder_12
    ATTR_ACCUM_MODE = Merge Incoming List
    ATTR_CONFLICT_RES = Use Original
    INDEX_ATTR = _element_index
    LIST_ATTR = DayPropertyType.namedDay{}
    LIST_FOUND -> AttributeRenamer_13
AttributeRenamer_13
    ATTR_LIST = DayPropertyType.namedDay,namedDay,
    -> TQ_NamedDay (writer GEOPACKAGE_1)
TQ_NamedDay (writer GEOPACKAGE_1)
    attributes: parentFeature_ID text(50), timeInterval_ID mediumint, dayPeriod_ID mediumint, namedDay text(50)

Bookmark: NamedPeriod
ListExploder_13
    ATTR_ACCUM_MODE = Merge Incoming List
    ATTR_CONFLICT_RES = Use Original
    INDEX_ATTR = _element_index
    LIST_ATTR = DayPropertyType.namedPeriod{}
    LIST_FOUND -> AttributeRenamer_14
AttributeRenamer_14
    ATTR_LIST = DayPropertyType.namedPeriod,namedPeriod,
    -> TQ_NamedPeriod (writer GEOPACKAGE_1)
TQ_NamedPeriod (writer GEOPACKAGE_1)
    attributes: parentFeature_ID text(50), timeInterval_ID mediumint, dayPeriod_ID mediumint, namedPeriod text(50)

Bookmark: Time element
TQ_Day_Time_Join (writer GEOPACKAGE_1)
    attributes: parentFeature_ID text(50), timeInterval_ID mediumint, dayPeriod_ID mediumint, timePeriod_ID mediumint

Bookmark: TimeRange
ListExploder_15
    ATTR_ACCUM_MODE = Merge Incoming List
    ATTR_CONFLICT_RES = Use Original
    INDEX_ATTR = _element_index
    LIST_ATTR = TimePropertyType.timeRange{}
    LIST_FOUND -> AttributeRenamer_15
AttributeRenamer_15
    ATTR_LIST = TimeRangeType.startTime,startTime,,TimeRangeType.endTime,endTime,
    -> TQ_TimeRange (writer GEOPACKAGE_1)
TQ_TimeRange (writer GEOPACKAGE_1)
    attributes: parentFeature_ID text(50), timeInterval_ID mediumint, dayPeriod_ID mediumint, timePeriod_ID mediumint, startTime text(10), endTime text(10)

Bookmark: NamedTime
ListExploder_16
    ATTR_ACCUM_MODE = Merge Incoming List
    ATTR_CONFLICT_RES = Use Original
    INDEX_ATTR = _element_index
    LIST_ATTR = TimePropertyType.namedTime{}
    LIST_FOUND -> AttributeRenamer_16
AttributeRenamer_16
    ATTR_LIST = TimePropertyType.namedTime,namedTime,
    -> TQ_NamedTime (writer GEOPACKAGE_1)
TQ_NamedTime (writer GEOPACKAGE_1)
    attributes: parentFeature_ID text(50), timeInterval_ID mediumint, dayPeriod_ID mediumint, timePeriod_ID mediumint, namedTime text(50)
