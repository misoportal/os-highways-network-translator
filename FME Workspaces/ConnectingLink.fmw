FME workspace ConnectingLink.fmw

Parameters:
- SourceDataset_GML = $(PATHS_DATA_INPUT_FOLDER)\Highways_Path_ConnectingLink_*.gml*   # Source ConnectingLink GML File(s)
- DestDataset_GEOPACKAGE = $(MIDDLE_FOLDER)\ConnectingLink.gpkg   # Middle ConnectingLink Geopackage File
- DestDataset_GEOPACKAGE_3 = ZeroLengthLine   # GeoPackage File

Readers:
- GML_1: GML from $(SourceDataset_GML)

Writers:
- GEOPACKAGE_1: GEOPACKAGE to $(DestDataset_GEOPACKAGE)
- GEOPACKAGE_2: GEOPACKAGE to $(DestDataset_GEOPACKAGE_3)

Note: Set input to local GML files
ConnectingLink (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, reasonForChange xml_buffer, reasonForChange.codeSpace xml_buffer, geometry xml_geometry, fictitious xml_boolean, pathNode.nilReason xml_buffer, pathNode.gml_remoteSchema xml_buffer, pathNode.xlink_href xml_buffer, pathNode.owns xml_boolean, connectingNode.nilReason xml_buffer, connectingNode.gml_remoteSchema xml_buffer, connectingNode.xlink_href xml_buffer, connectingNode.owns xml_boolean
    -> AttributeRenamer
Note: Rename ID to TOID and other attributes to make easier to read
Note: Creates geometry for connecting roadlinks and pathlinks
AttributeRenamer
    ATTR_TABLE:
      RENAME_SET_DEFAULT gml_id > TOID
      RENAME_SET_DEFAULT inspireId.Identifier.localId > identifier
      RENAME_SET_DEFAULT pathNode.xlink_href > pathNode
      RENAME_SET_DEFAULT connectingNode.xlink_href > connectingNode
      RENAME_SET_DEFAULT fme_basename > chunkname
    -> TestFilter
DateFormatter
    DATE_ATTR = beginLifespanVersion
    FMT = FME Date (%Y%m%d)
    INVALID_DATE_VALUE = _FME_NO_OP_
    SRCFMT = Unknown - Automatic Detection
    -> StringReplacer
Note: Remove unwanted #
StringReplacer
    CASE = NO
    FIND_TEXT = #
    NO_MATCH = _FME_NO_OP_
    REGEXP = NO
    SRC_ATTRS = pathNode,connectingNode
    -> ConnectingLink (writer GEOPACKAGE_1)
Note: fictitious set to char (not boolean) so that True or False will appear in the data; / ESRI defaults to 1 or 0 respectively.
Note: change output to prefered format
ConnectingLink (writer GEOPACKAGE_1)
    attributes: TOID text(20), identifier text(37), fictitious text(5), connectingNode text(20), pathNode text(20), beginLifespanVersion text(20), reasonForChange text(32), chunkname text(50)

Bookmark: miso addition
TestFilter
    DEFAULT_VALUE = <UNFILTERED>
    TEST_LIST = "BOOL_OP,AND,COMPOSITE_TEST,""""""<Unused>"""""",TEST_CLAUSE,TEST @Length() = 0",ZeroLength
    <UNFILTERED> -> DateFormatter
    ZeroLength -> ConnectingLink (writer GEOPACKAGE_2)
ConnectingLink (writer GEOPACKAGE_2)
    attributes: TOID text(20), chunkname text(50)
