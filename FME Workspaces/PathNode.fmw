FME workspace PathNode.fmw

Parameters:
- SourceDataset_GML = $(PATHS_DATA_INPUT_FOLDER)\GZ\Highways_P*_PathNode_*.gml.gz   # Source PathNode GML File(s)
- DestDataset_GEOPACKAGE = $(MIDDLE_FOLDER)\PathNode.gpkg   # Middle PathNode Geopackage File

Readers:
- GML_1: GML from $(SourceDataset_GML)

Writers:
- GEOPACKAGE_1: GEOPACKAGE to $(DestDataset_GEOPACKAGE)

Note: Change input to local GML
PathNode (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, geometry xml_geometry, spokeEnd{}.owns xml_boolean, spokeEnd{}.nilReason xml_buffer, spokeEnd{}.gml_remoteSchema xml_buffer, spokeEnd{}.xlink_href xml_buffer, spokeEnd{}.xsi_nil xml_boolean, spokeStart{}.owns xml_boolean, spokeStart{}.nilReason xml_buffer, spokeStart{}.gml_remoteSchema xml_buffer, spokeStart{}.xlink_href xml_buffer, spokeStart{}.xsi_nil xml_boolean, geographicalName.nilReason xml_buffer, geographicalName.xsi_nil xml_boolean, geographicalName.GeographicalName.language xml_buffer,
      geographicalName.GeographicalName.language.nilReason xml_buffer, geographicalName.GeographicalName.language.xsi_nil xml_boolean, geographicalName.GeographicalName.nativeness.owns xml_boolean, geographicalName.GeographicalName.nativeness.nilReason xml_buffer, geographicalName.GeographicalName.nativeness.gml_remoteSchema xml_buffer, geographicalName.GeographicalName.nativeness.xlink_href xml_buffer, geographicalName.GeographicalName.nativeness.xsi_nil xml_boolean, geographicalName.GeographicalName.nameStatus.owns xml_boolean, geographicalName.GeographicalName.nameStatus.nilReason xml_buffer, geographicalName.GeographicalName.nameStatus.gml_remoteSchema xml_buffer, geographicalName.GeographicalName.nameStatus.xlink_href xml_buffer, geographicalName.GeographicalName.nameStatus.xsi_nil xml_boolean, geographicalName.GeographicalName.sourceOfName xml_buffer, geographicalName.GeographicalName.sourceOfName.nilReason xml_buffer, geographicalName.GeographicalName.sourceOfName.xsi_nil xml_boolean, geographicalName.GeographicalName.pronunciation.nilReason xml_buffer, geographicalName.GeographicalName.pronunciation.xsi_nil xml_boolean, geographicalName.GeographicalName.pronunciation.PronunciationOfName.pronunciationSoundLink xml_buffer, geographicalName.GeographicalName.pronunciation.PronunciationOfName.pronunciationSoundLink.nilReason xml_buffer, geographicalName.GeographicalName.pronunciation.PronunciationOfName.pronunciationSoundLink.xsi_nil xml_boolean, geographicalName.GeographicalName.pronunciation.PronunciationOfName.pronunciationIPA xml_buffer, geographicalName.GeographicalName.pronunciation.PronunciationOfName.pronunciationIPA.nilReason xml_buffer, geographicalName.GeographicalName.pronunciation.PronunciationOfName.pronunciationIPA.xsi_nil xml_boolean, geographicalName.GeographicalName.spelling{}.SpellingOfName.text xml_buffer, geographicalName.GeographicalName.spelling{}.SpellingOfName.script xml_buffer, geographicalName.GeographicalName.spelling{}.SpellingOfName.script.nilReason xml_buffer, geographicalName.GeographicalName.spelling{}.SpellingOfName.script.xsi_nil xml_boolean, geographicalName.GeographicalName.spelling{}.SpellingOfName.transliterationScheme xml_buffer, geographicalName.GeographicalName.spelling{}.SpellingOfName.transliterationScheme.nilReason xml_buffer, geographicalName.GeographicalName.spelling{}.SpellingOfName.transliterationScheme.xsi_nil xml_boolean,
      geographicalName.GeographicalName.grammaticalGender.owns xml_boolean, geographicalName.GeographicalName.grammaticalGender.nilReason xml_buffer, geographicalName.GeographicalName.grammaticalGender.gml_remoteSchema xml_buffer, geographicalName.GeographicalName.grammaticalGender.xlink_href xml_buffer, geographicalName.GeographicalName.grammaticalGender.xsi_nil xml_boolean, geographicalName.GeographicalName.grammaticalNumber.owns xml_boolean, geographicalName.GeographicalName.grammaticalNumber.nilReason xml_buffer, geographicalName.GeographicalName.grammaticalNumber.gml_remoteSchema xml_buffer, geographicalName.GeographicalName.grammaticalNumber.xlink_href xml_buffer, geographicalName.GeographicalName.grammaticalNumber.xsi_nil xml_boolean, validFrom xml_datetime, validFrom.nilReason xml_buffer, validFrom.xsi_nil xml_boolean, validTo xml_datetime, validTo.nilReason xml_buffer, validTo.xsi_nil xml_boolean, formOfRoadNode.owns xml_boolean, formOfRoadNode.nilReason xml_buffer, formOfRoadNode.gml_remoteSchema xml_buffer, formOfRoadNode.xlink_href xml_buffer, formOfRoadNode.xsi_nil xml_boolean, reasonForChange xml_buffer, reasonForChange.codeSpace xml_buffer, classification xml_buffer, classification.codeSpace xml_buffer
    -> AttributeRenamer_2
Note: Rename attributes
AttributeRenamer_2
    ATTR_LIST = gml_id,TOID,,inspireId.Identifier.localId,identifier,,fme_basename,chunkname,
    -> DateFormatter
Note: Change output to prefered format
PathNode (writer GEOPACKAGE_1)
    attributes: TOID text(20), identifier text(16), formofRoadNode text(21), classification text(19), beginLifespanVersion text(20), reasonForChange text(32), validFrom text(20), chunkname text(50)

Bookmark: Create PathNode
Note: reformat as DMY
DateFormatter
    DATE_ATTR = beginLifespanVersion
    FMT = FME Date (%Y%m%d)
    INVALID_DATE_VALUE = _FME_NO_OP_
    SRCFMT = Unknown - Automatic Detection
    -> TestFilter
AttributeRenamer
    ATTR_LIST = inspireId.Identifier.namespace,identifierNamespace,,inspireId.Identifier.versionId,identifierVersionId,
    -> AttributeSplitter
Note: The attribute value for "formOfRoadNode" is held as a / URL therefore to extract the value from the URL / the attribute needs splitting after every "/". This / action will create a list. The values after the last / "/" will contain the attribute value.
AttributeSplitter
    ATTR_NAME = formOfRoadNode.xlink_href
    DELIMITER = /
    DROP_EMPTY_PARTS = No
    LIST_NAME = form_list
    TRIM_OPTION = Both
    -> AttributeRenamer_4
Note: Rename formOfRoadNode
AttributeRenamer_4
    ATTR_LIST = form_list{5},formofRoadNode,
    -> PathNode (writer GEOPACKAGE_1)

Bookmark: miso addition
TestFilter
    DEFAULT_VALUE = <UNFILTERED>
    TEST_LIST = "BOOL_OP,OR,COMPOSITE_TEST,""""""<Unused>"""""",TEST_CLAUSE,TEST validFrom ATTRIBUTE_HAS_A_VALUE """,ValidFrom
    ValidFrom -> DateFormatter_2
    <UNFILTERED> -> AttributeRenamer
DateFormatter_2
    DATE_ATTR = validFrom
    FMT = FME Date (%Y%m%d)
    INVALID_DATE_VALUE = _FME_NO_OP_
    SRCFMT = Unknown - Automatic Detection
    -> AttributeRenamer
