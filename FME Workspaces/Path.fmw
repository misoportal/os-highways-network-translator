FME workspace Path.fmw

Parameters:
- SourceDataset_GML = $(PATHS_DATA_INPUT_FOLDER)\Highways_P*_Path_*.gml*   # Source Path GML File(s)
- DestDataset_GEOPACKAGE = $(MIDDLE_FOLDER)\Path.gpkg   # Middle Path Geopackage File

Readers:
- GML_1: GML from $(SourceDataset_GML)

Writers:
- GEOPACKAGE_1: GEOPACKAGE to $(DestDataset_GEOPACKAGE)

Note: Change input to local GML
Path (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, link{}.nilReason xml_buffer, link{}.gml_remoteSchema xml_buffer, link{}.xlink_href xml_buffer, link{}.owns xml_boolean, geographicalName.nilReason xml_buffer, geographicalName.xsi_nil xml_boolean, geographicalName.GeographicalName.language xml_buffer, geographicalName.GeographicalName.language.nilReason xml_buffer, geographicalName.GeographicalName.language.xsi_nil xml_boolean, geographicalName.GeographicalName.nativeness.owns xml_boolean, geographicalName.GeographicalName.nativeness.nilReason xml_buffer, geographicalName.GeographicalName.nativeness.gml_remoteSchema xml_buffer, geographicalName.GeographicalName.nativeness.xlink_href xml_buffer, geographicalName.GeographicalName.nativeness.xsi_nil xml_boolean,
      geographicalName.GeographicalName.nameStatus.owns xml_boolean, geographicalName.GeographicalName.nameStatus.nilReason xml_buffer, geographicalName.GeographicalName.nameStatus.gml_remoteSchema xml_buffer, geographicalName.GeographicalName.nameStatus.xlink_href xml_buffer, geographicalName.GeographicalName.nameStatus.xsi_nil xml_boolean, geographicalName.GeographicalName.sourceOfName xml_buffer, geographicalName.GeographicalName.sourceOfName.nilReason xml_buffer, geographicalName.GeographicalName.sourceOfName.xsi_nil xml_boolean, geographicalName.GeographicalName.pronunciation.nilReason xml_buffer, geographicalName.GeographicalName.pronunciation.xsi_nil xml_boolean, geographicalName.GeographicalName.pronunciation.PronunciationOfName.pronunciationSoundLink xml_buffer, geographicalName.GeographicalName.pronunciation.PronunciationOfName.pronunciationSoundLink.nilReason xml_buffer, geographicalName.GeographicalName.pronunciation.PronunciationOfName.pronunciationSoundLink.xsi_nil xml_boolean, geographicalName.GeographicalName.pronunciation.PronunciationOfName.pronunciationIPA xml_buffer, geographicalName.GeographicalName.pronunciation.PronunciationOfName.pronunciationIPA.nilReason xml_buffer, geographicalName.GeographicalName.pronunciation.PronunciationOfName.pronunciationIPA.xsi_nil xml_boolean, geographicalName.GeographicalName.spelling{}.SpellingOfName.text xml_buffer, geographicalName.GeographicalName.spelling{}.SpellingOfName.script xml_buffer, geographicalName.GeographicalName.spelling{}.SpellingOfName.script.nilReason xml_buffer, geographicalName.GeographicalName.spelling{}.SpellingOfName.script.xsi_nil xml_boolean, geographicalName.GeographicalName.spelling{}.SpellingOfName.transliterationScheme xml_buffer, geographicalName.GeographicalName.spelling{}.SpellingOfName.transliterationScheme.nilReason xml_buffer, geographicalName.GeographicalName.spelling{}.SpellingOfName.transliterationScheme.xsi_nil xml_boolean, geographicalName.GeographicalName.grammaticalGender.owns xml_boolean, geographicalName.GeographicalName.grammaticalGender.nilReason xml_buffer, geographicalName.GeographicalName.grammaticalGender.gml_remoteSchema xml_buffer, geographicalName.GeographicalName.grammaticalGender.xlink_href xml_buffer, geographicalName.GeographicalName.grammaticalGender.xsi_nil xml_boolean, geographicalName.GeographicalName.grammaticalNumber.owns xml_boolean, geographicalName.GeographicalName.grammaticalNumber.nilReason xml_buffer,
      geographicalName.GeographicalName.grammaticalNumber.gml_remoteSchema xml_buffer, geographicalName.GeographicalName.grammaticalNumber.xlink_href xml_buffer, geographicalName.GeographicalName.grammaticalNumber.xsi_nil xml_boolean, validFrom xml_datetime, validFrom.nilReason xml_buffer, validFrom.xsi_nil xml_boolean, validTo xml_datetime, validTo.nilReason xml_buffer, validTo.xsi_nil xml_boolean, post{}.owns xml_boolean, post{}.nilReason xml_buffer, post{}.gml_remoteSchema xml_buffer, post{}.xlink_href xml_buffer, post{}.xsi_nil xml_boolean, localRoadCode xml_buffer, localRoadCode.nilReason xml_buffer, localRoadCode.xsi_nil xml_boolean, nationalRoadCode xml_buffer, nationalRoadCode.nilReason xml_buffer, nationalRoadCode.xsi_nil xml_boolean, reasonForChange xml_buffer, reasonForChange.codeSpace xml_buffer, pathName{} xml_buffer, pathName{}.xml_lang xml_buffer
    -> AttributeRenamer
Note: Rename TOID
AttributeRenamer
    ATTR_LIST = gml_id,TOID,,inspireId.Identifier.localId,identifier,,fme_basename,chunkname,
    -> TestFilter
    -> ListExploder
DateFormatter
    DATE_ATTR = beginLifespanVersion
    FMT = FME Date (%Y%m%d)
    INVALID_DATE_VALUE = _FME_NO_OP_
    SRCFMT = Unknown - Automatic Detection
    -> ListIndexer_2
Note: Change output to prefered format
Path (writer GEOPACKAGE_1)
    attributes: TOID text(20), identifier text(16), pathName1_text text(255), pathName1_lang text(3), pathName2_text text(255), pathName2_lang text(3), beginLifespanVersion text(20), reasonForChange text(32), validFrom text(20), chunkname text(50)

Bookmark: miso addition
TestFilter
    DEFAULT_VALUE = <UNFILTERED>
    TEST_LIST = "BOOL_OP,OR,COMPOSITE_TEST,""""""<Unused>"""""",TEST_CLAUSE,TEST validFrom ATTRIBUTE_HAS_A_VALUE """,ValidFrom
    ValidFrom -> DateFormatter_2
    <UNFILTERED> -> DateFormatter
DateFormatter_2
    DATE_ATTR = validFrom
    FMT = FME Date (%Y%m%d)
    INVALID_DATE_VALUE = _FME_NO_OP_
    SRCFMT = Unknown - Automatic Detection
    -> DateFormatter

Bookmark: Extract muliple names
ListIndexer_2
    INDEX = 0
    LIST_ATTR = pathName{}
    PREFIX = pathName1_
    -> AttributeRenamer_2
AttributeRenamer_2
    ATTR_LIST = pathName1_pathName,pathName1_text,,pathName1_xml_lang,pathName1_lang,
    -> ListIndexer_3
ListIndexer_3
    INDEX = 1
    LIST_ATTR = pathName{}
    PREFIX = pathName2_
    -> AttributeRenamer_3
AttributeRenamer_3
    ATTR_LIST = pathName2_pathName,pathName2_text,,pathName2_xml_lang,pathName2_lang,
    -> Path (writer GEOPACKAGE_1)

Bookmark: Create Path to PathLink table
ListExploder
    ATTR_ACCUM_MODE = Merge Incoming List
    ATTR_CONFLICT_RES = Use Original
    INDEX_ATTR = _element_index
    LIST_ATTR = link{}
    LIST_FOUND -> AttributeRenamer_4
AttributeRenamer_4
    ATTR_LIST = xlink_href,pathLink_TOID,,TOID,path_TOID,
    -> StringReplacer
Note: Remove #
StringReplacer
    CASE = no
    FIND_TEXT = #
    NO_MATCH = _FME_NO_OP_
    REGEXP = no
    SRC_ATTRS = pathLink_TOID
    -> Path_Ref_PathLink (writer GEOPACKAGE_1)
Path_Ref_PathLink (writer GEOPACKAGE_1)
    attributes: path_TOID text(20), pathLink_TOID text(20)
