FME workspace PathLink.fmw

Parameters:
- SourceDataset_GML = $(PATHS_DATA_INPUT_FOLDER)\Highways_P*_PathLink_*.gml*   # Source PathLink GML File(s)
- DestDataset_GEOPACKAGE = $(MIDDLE_FOLDER)\PathLink.gpkg   # Middle PathLink Geopackage File

Readers:
- GML_1: GML from $(SourceDataset_GML)

Writers:
- GEOPACKAGE_1: GEOPACKAGE to $(DestDataset_GEOPACKAGE)

Note: Change input to local GML
PathLink (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, centrelineGeometry xml_geometry, fictitious xml_boolean, endNode.owns xml_boolean, endNode.nilReason xml_buffer, endNode.gml_remoteSchema xml_buffer, endNode.xlink_href xml_buffer, startNode.owns xml_boolean, startNode.nilReason xml_buffer, startNode.gml_remoteSchema xml_buffer, startNode.xlink_href xml_buffer, geographicalName.nilReason xml_buffer, geographicalName.xsi_nil xml_boolean, geographicalName.GeographicalName.language xml_buffer, geographicalName.GeographicalName.language.nilReason xml_buffer,
      geographicalName.GeographicalName.language.xsi_nil xml_boolean, geographicalName.GeographicalName.nativeness.owns xml_boolean, geographicalName.GeographicalName.nativeness.nilReason xml_buffer, geographicalName.GeographicalName.nativeness.gml_remoteSchema xml_buffer, geographicalName.GeographicalName.nativeness.xlink_href xml_buffer, geographicalName.GeographicalName.nativeness.xsi_nil xml_boolean, geographicalName.GeographicalName.nameStatus.owns xml_boolean, geographicalName.GeographicalName.nameStatus.nilReason xml_buffer, geographicalName.GeographicalName.nameStatus.gml_remoteSchema xml_buffer, geographicalName.GeographicalName.nameStatus.xlink_href xml_buffer, geographicalName.GeographicalName.nameStatus.xsi_nil xml_boolean, geographicalName.GeographicalName.sourceOfName xml_buffer, geographicalName.GeographicalName.sourceOfName.nilReason xml_buffer, geographicalName.GeographicalName.sourceOfName.xsi_nil xml_boolean, geographicalName.GeographicalName.pronunciation.nilReason xml_buffer, geographicalName.GeographicalName.pronunciation.xsi_nil xml_boolean, geographicalName.GeographicalName.pronunciation.PronunciationOfName.pronunciationSoundLink xml_buffer, geographicalName.GeographicalName.pronunciation.PronunciationOfName.pronunciationSoundLink.nilReason xml_buffer, geographicalName.GeographicalName.pronunciation.PronunciationOfName.pronunciationSoundLink.xsi_nil xml_boolean, geographicalName.GeographicalName.pronunciation.PronunciationOfName.pronunciationIPA xml_buffer, geographicalName.GeographicalName.pronunciation.PronunciationOfName.pronunciationIPA.nilReason xml_buffer, geographicalName.GeographicalName.pronunciation.PronunciationOfName.pronunciationIPA.xsi_nil xml_boolean, geographicalName.GeographicalName.spelling{}.SpellingOfName.text xml_buffer, geographicalName.GeographicalName.spelling{}.SpellingOfName.script xml_buffer, geographicalName.GeographicalName.spelling{}.SpellingOfName.script.nilReason xml_buffer, geographicalName.GeographicalName.spelling{}.SpellingOfName.script.xsi_nil xml_boolean, geographicalName.GeographicalName.spelling{}.SpellingOfName.transliterationScheme xml_buffer, geographicalName.GeographicalName.spelling{}.SpellingOfName.transliterationScheme.nilReason xml_buffer, geographicalName.GeographicalName.spelling{}.SpellingOfName.transliterationScheme.xsi_nil xml_boolean, geographicalName.GeographicalName.grammaticalGender.owns xml_boolean,
      geographicalName.GeographicalName.grammaticalGender.nilReason xml_buffer, geographicalName.GeographicalName.grammaticalGender.gml_remoteSchema xml_buffer, geographicalName.GeographicalName.grammaticalGender.xlink_href xml_buffer, geographicalName.GeographicalName.grammaticalGender.xsi_nil xml_boolean, geographicalName.GeographicalName.grammaticalNumber.owns xml_boolean, geographicalName.GeographicalName.grammaticalNumber.nilReason xml_buffer, geographicalName.GeographicalName.grammaticalNumber.gml_remoteSchema xml_buffer, geographicalName.GeographicalName.grammaticalNumber.xlink_href xml_buffer, geographicalName.GeographicalName.grammaticalNumber.xsi_nil xml_boolean, validFrom xml_datetime, validFrom.nilReason xml_buffer, validFrom.xsi_nil xml_boolean, validTo xml_datetime, validTo.nilReason xml_buffer, validTo.xsi_nil xml_boolean, reasonForChange xml_buffer, reasonForChange.codeSpace xml_buffer, formOfWay xml_buffer, formOfWay.codeSpace xml_buffer, pathName{} xml_buffer, pathName{}.xml_lang xml_buffer, alternateName{} xml_buffer, alternateName{}.xml_lang xml_buffer, provenance xml_buffer, provenance.codeSpace xml_buffer, surfaceType xml_buffer, surfaceType.codeSpace xml_buffer, cycleFacility.CycleFacilityType.cycleFacility xml_buffer, cycleFacility.CycleFacilityType.cycleFacility.codeSpace xml_buffer, cycleFacility.CycleFacilityType.wholeLink xml_boolean,
      cycleFacility.CycleFacilityType.wholeLink.nilReason xml_buffer, cycleFacility.CycleFacilityType.wholeLink.xsi_nil xml_boolean, matchStatus xml_buffer, matchStatus.codeSpace xml_buffer, length xml_real64, length.uom xml_buffer, alternateIdentifier{}.ThematicIdentifier.identifier xml_buffer, alternateIdentifier{}.ThematicIdentifier.identifierScheme xml_buffer, startGradeSeparation xml_int64, endGradeSeparation xml_int64, elevationGain.ElevationGainType.inDirection xml_real64, elevationGain.ElevationGainType.inDirection.uom xml_buffer, elevationGain.ElevationGainType.inOppositeDirection xml_real64, elevationGain.ElevationGainType.inOppositeDirection.uom xml_buffer, relatedArea{}.nilReason xml_buffer, relatedArea{}.gml_remoteSchema xml_buffer, relatedArea{}.xlink_href xml_buffer, relatedArea{}.owns xml_boolean, formsPartOf{}.nilReason xml_buffer, formsPartOf{}.gml_remoteSchema xml_buffer, formsPartOf{}.xlink_href xml_buffer, formsPartOf{}.owns xml_boolean
    -> AttributeRenamer
Note: Rename TOID
AttributeRenamer
    ATTR_LIST = gml_id,TOID,,inspireId.Identifier.localId,identifier,,endNode.xlink_href,endNode,,startNode.xlink_href,startNode,,fme_basename,chunkname,
    -> TestFilter_2
Note: Change output to prefered format
DateFormatter
    DATE_ATTR = beginLifespanVersion
    FMT = FME Date (%Y%m%d)
    INVALID_DATE_VALUE = _FME_NO_OP_
    SRCFMT = Unknown - Automatic Detection
    -> ListExploder
    -> ListExploder_2
    -> ListIndexer

Bookmark: miso addition
TestFilter_2
    DEFAULT_VALUE = <UNFILTERED>
    TEST_LIST = "BOOL_OP,OR,COMPOSITE_TEST,""""""<Unused>"""""",TEST_CLAUSE,TEST validFrom ATTRIBUTE_HAS_A_VALUE """,ValidFrom
    ValidFrom -> DateFormatter_2
    <UNFILTERED> -> DateFormatter
DateFormatter_2
    DATE_ATTR = validFrom
    FMT = FME Date (%Y%m%d)
    INVALID_DATE_VALUE = _FME_NO_OP_
    SRCFMT = Unknown - Automatic Detection
    -> DateFormatter

Bookmark: alternateIdentifier
ListExploder
    ATTR_ACCUM_MODE = Merge Incoming List
    ATTR_CONFLICT_RES = Use Original
    INDEX_ATTR = _element_index
    LIST_ATTR = alternateIdentifier{}
    LIST_FOUND -> AttributeRenamer_2
AttributeRenamer_2
    ATTR_LIST = ThematicIdentifier.identifier,alternateIdentifier,,ThematicIdentifier.identifierScheme,alternateIdentifierSchema,
    -> PathLink_AlternateIdentifier (writer GEOPACKAGE_1)
PathLink_AlternateIdentifier (writer GEOPACKAGE_1)
    attributes: TOID text(20), alternateIdentifier text(20), alternateIdentifierSchema text(50)

Bookmark: formsPartOf
ListExploder_2
    ATTR_ACCUM_MODE = Merge Incoming List
    ATTR_CONFLICT_RES = Use Original
    INDEX_ATTR = _element_index
    LIST_ATTR = formsPartOf{}
    LIST_FOUND -> TestFilter
TestFilter
    DEFAULT_VALUE = <UNFILTERED>
    TEST_LIST = BOOL_OP,OR,COMPOSITE_TEST,<Unused>,TEST_CLAUSE,"TEST @Value(xlink_href) CONTAINS #osgb",osgb,BOOL_OP,OR,COMPOSITE_TEST,<Unused>,TEST_CLAUSE,"TEST @Value(xlink_href) CONTAINS #usrn",usrn
    osgb -> AttributeCreator
    usrn -> AttributeCreator_2
    <UNFILTERED> -> AttributeCreator_3
AttributeCreator
    ATTR_LIST = refType,Road
    -> AttributeRenamer_9
AttributeCreator_2
    ATTR_LIST = refType,Street
    -> AttributeRenamer_9
AttributeCreator_3
    ATTR_LIST = refType,Other
    -> AttributeRenamer_9
AttributeRenamer_9
    ATTR_LIST = xlink_href,formsPartOf,
    -> StringReplacer_2
StringReplacer_2
    CASE = no
    FIND_TEXT = #
    NO_MATCH = _FME_NO_OP_
    REGEXP = no
    SRC_ATTRS = formsPartOf
    -> PathLink_FormsPartOf (writer GEOPACKAGE_1)
PathLink_FormsPartOf (writer GEOPACKAGE_1)
    attributes: TOID text(20), formsPartOf text(20), refType text(20)

Bookmark: PathLink
ListIndexer
    INDEX = 0
    LIST_ATTR = pathName{}
    PREFIX = pathName1_
    -> AttributeRenamer_3
AttributeRenamer_3
    ATTR_LIST = pathName1_pathName,pathName1_Text,,pathName1_xml_lang,pathName1_Language,
    -> ListIndexer_2
ListIndexer_2
    INDEX = 1
    LIST_ATTR = pathName{}
    PREFIX = pathName2_
    -> AttributeRenamer_4
AttributeRenamer_4
    ATTR_LIST = pathName2_pathName,pathName2_Text,,pathName2_xml_lang,pathName2_Language,
    -> ListIndexer_5
ListIndexer_5
    INDEX = 0
    LIST_ATTR = alternateName{}
    PREFIX = alternativeName1_
    -> AttributeRenamer_6
AttributeRenamer_6
    ATTR_LIST = alternativeName1_alternateName,alternativeName1_Text,,alternativeName1_xml_lang,alternativeName1_Language,
    -> ListIndexer_6
ListIndexer_6
    INDEX = 1
    LIST_ATTR = alternateName{}
    PREFIX = alternativeName2_
    -> AttributeRenamer_7
AttributeRenamer_7
    ATTR_LIST = alternativeName2_alternateName,alternativeName2_Text,,localName2_xml_lang,alternativeName2_Language,
    -> StringReplacer
Note: Remove #
StringReplacer
    CASE = no
    FIND_TEXT = #
    NO_MATCH = _FME_NO_OP_
    REGEXP = no
    SRC_ATTRS = endNode,startNode
    -> AttributeCreator_4
PathLink (writer GEOPACKAGE_1)
    attributes: TOID text(20), identifier text(16), fictitious text(5), cycleFacility text(120), cycleFacilityWholeLink text(1), startNode text(20), startGradeSeparation mediumint, endNode text(20), endGradeSeparation mediumint, formOfWay text(42), pathName1_Text text(255), pathName1_Language text(3), pathName2_Text text(255), pathName2_Language text(3), alternativeName1_Text text(255), alternativeName1_Language text(5), alternativeName2_Text text(255), alternativeName2_Language text(5), provenance text(40), surfaceType text(13), matchStatus text(39), length double, beginLifespanVersion text, reasonForChange text(32), validFrom text(20), chunkname text(50)

Bookmark: miso addition
AttributeCreator_4
    ATTR_TABLE:
      SET_TO cycleFacilityWholeLink = FME_CONDITIONAL:DEFAULT_VALUE'_FME_NO_OP_'BOOL_OP;OR;COMPOSITE_TEST;<Unused>;TEST @Value(cycleFacility.CycleFacilityType.wholeLink) = true'T'BOOL_OP;OR;COMPOSITE_TEST;<Unused>;TEST @Value(cycleFacility.CycleFacilityType.wholeLink) = false'F'BOOL_OP;OR;COMPOSITE_TEST;<Unused>;TEST @Value(cycleFacility.CycleFacilityType.wholeLink.nilReason) = unknown'?'FME_NUM_CONDITIONS4___
      SET_TO cycleFacility = @Value(cycleFacility.CycleFacilityType.cycleFacility)
    -> PathLink (writer GEOPACKAGE_1)
