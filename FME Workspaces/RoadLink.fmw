FME workspace RoadLink.fmw

Parameters:
- SourceDataset_GML = $(ROADS_DATA_INPUT_FOLDER)\Highways_Rrami_RoadLink_*.gml*   # Source RoadLink GML File(s)
- DestDataset_GEOPACKAGE = $(MIDDLE_FOLDER)\RoadLink.gpkg   # Middle RoadLink Geopackage File

Readers:
- GML_1: GML from $(SourceDataset_GML)

Writers:
- GEOPACKAGE_1: GEOPACKAGE to $(DestDataset_GEOPACKAGE)

Note: Change to local input
RoadLink (reader GML_1)
    attributes: alternateIdentifier{}.ThematicIdentifier.identifier xml_char(20), alternateIdentifier{}.ThematicIdentifier.identifierScheme xml_char(39), alternateName{} xml_char(24), beginLifespanVersion xml_char(24), cycleFacility.CycleFacilityType.cycleFacility xml_char(39), cycleFacility.CycleFacilityType.cycleFacility.codeSpace xml_char(62), cycleFacility.CycleFacilityType.wholeLink xml_char(1), cycleFacility.CycleFacilityType.wholeLink.nilReason xml_char(8), cycleFacility.CycleFacilityType.wholeLink.xsi_nil xml_char(5), directionality.owns xml_char(6), directionality.xlink_href xml_char(76), elevationGain.ElevationGainType.inDirection xml_decimal(4,0), elevationGain.ElevationGainType.inDirection.uom xml_char(2), elevationGain.ElevationGainType.inOppositeDirection xml_decimal(4,0), elevationGain.ElevationGainType.inOppositeDirection.uom xml_char(2), endGradeSeparation xml_decimal(2,0), endNode.owns xml_char(6), endNode.xlink_href xml_char(22), fictitious xml_char(6), formOfWay xml_char(32), formsPartOf{}.owns xml_char(6), formsPartOf{}.xlink_href xml_char(22), inNetwork{}.owns xml_char(6), inNetwork{}.xlink_href xml_char(18), inspireId.Identifier.localId xml_decimal(17,0), inspireId.Identifier.namespace xml_char(19), length xml_decimal(7,2), length.uom xml_char(2), matchStatus xml_char(26), matchStatus.codeSpace xml_char(61),
      numberOfLanes{}.NumberOfLanesType.direction.owns xml_char(6), numberOfLanes{}.NumberOfLanesType.direction.xlink_href xml_char(76), numberOfLanes{}.NumberOfLanesType.minMaxNumberOfLanes xml_char(8), numberOfLanes{}.NumberOfLanesType.numberOfLanes xml_decimal(2,0), operationalState xml_char(5), operationalState.codeSpace xml_char(66), primaryRoute xml_char(6), provenance xml_char(16), provenance.codeSpace xml_char(66), reasonForChange xml_char(4), reasonForChange.codeSpace xml_char(47), relatedRoadArea{}.owns xml_char(6), relatedRoadArea{}.xlink_href xml_char(22), roadClassification xml_char(22), roadClassification.codeSpace xml_char(59), roadClassificationNumber xml_char(6), roadName{} xml_char(37), roadWidth.RoadWidthType.averageWidth xml_decimal(3,0), roadWidth.RoadWidthType.averageWidth.uom xml_char(2), roadWidth.RoadWidthType.confidenceLevel xml_decimal(2,0), roadWidth.RoadWidthType.minimumWidth xml_decimal(3,0), roadWidth.RoadWidthType.minimumWidth.uom xml_char(2), routeHierarchy xml_char(33), routeHierarchy.codeSpace xml_char(53), startGradeSeparation xml_decimal(2,0), startNode.owns xml_char(6), startNode.xlink_href xml_char(22), trunkRoad xml_char(6), validFrom xml_char(1), validFrom.nilReason xml_char(8),
      validFrom.xsi_nil xml_char(5), roadStructure xml_char(15)
    -> TestFilter_2
Note: Reformat date as DMY
DateFormatter
    DATE_ATTR = beginLifespanVersion
    FMT = FME Date (%Y%m%d)
    INVALID_DATE_VALUE = FME_NULL_VALUE
    SRCFMT = Unknown - Automatic Detection
    -> AttributeRenamer_5
Note: Rename attributes
AttributeRenamer_5
    ATTR_LIST = gml_id,TOID,,inspireId.Identifier.localId,identifier,,fme_basename,chunkname,
    -> ListExploder_3
    -> ListExploder_2
    -> ListIndexer
    -> ListExploder

Bookmark: miso addition
TestFilter_2
    DEFAULT_VALUE = <UNFILTERED>
    TEST_LIST = "BOOL_OP,OR,COMPOSITE_TEST,""""""<Unused>"""""",TEST_CLAUSE,TEST validFrom ATTRIBUTE_HAS_A_VALUE """,ValidFrom
    ValidFrom -> DateFormatter_2
    <UNFILTERED> -> DateFormatter
DateFormatter_2
    DATE_ATTR = validFrom
    FMT = FME Date (%Y%m%d)
    INVALID_DATE_VALUE = _FME_NO_OP_
    SRCFMT = Unknown - Automatic Detection
    -> DateFormatter

Bookmark: roadName
Note: roadName1
ListIndexer
    INDEX = 0
    LIST_ATTR = roadName{}
    PREFIX = roadName1_
    -> AttributeRenamer_2
Note: roadName1
AttributeRenamer_2
    ATTR_LIST = roadName1_roadName,roadName1,,roadName1_xml_lang,roadName1_Language,
    -> ListIndexer_2
Note: roadName2
ListIndexer_2
    INDEX = 1
    LIST_ATTR = roadName{}
    PREFIX = roadName2_
    -> AttributeRenamer_3
Note: roadName2
AttributeRenamer_3
    ATTR_LIST = roadName2_roadName,roadName2,,roadName2_xml_lang,roadName2_Language,
    -> ListIndexer_5

Bookmark: alternativeName
Note: alternativeName1
ListIndexer_5
    INDEX = 0
    LIST_ATTR = alternateName{}
    PREFIX = alternativeName1_
    -> AttributeRenamer_6
Note: alternativelName1
AttributeRenamer_6
    ATTR_LIST = alternativeName1_alternateName,alternativeName1,,alternativeName1_xml_lang,alternativeName1_Language,
    -> ListIndexer_6
Note: alternativeName2
ListIndexer_6
    INDEX = 1
    LIST_ATTR = alternateName{}
    PREFIX = alternativeName2_
    -> AttributeRenamer_7
Note: alternativeName2
AttributeRenamer_7
    ATTR_LIST = alternativeName2_alternateName,alternativeName2,,localName2_xml_lang,alternativeName2_Language,
    -> AttributeRenamer

Bookmark: Create the RoadLink feature
Note: Create lists for roadName and alternativeName and write to mulutiple attributes because the multiplicty for roadName and alternativeName is 0..2.
AttributeRenamer
    ATTR_LIST = inspireId.Identifier.localId,localId,,inspireId.Identifier.namespace,identifierNamespace,,inspireId.Identifier.versionId,identifierVersionId,,operationalState.OperationalStateType.state,operationalState_State,,operationalState.OperationalStateType.reason,operationsState_Reason,,startNode.xlink_href,startNode,,endNode.xlink_href,endNode,,operationalState.OperationalStateType.validTime.gml_TimePeriod.gml_beginPosition,operationalState_StartTime,,operationalState.OperationalStateType.validTime.gml_TimePeriod.gml_endPosition,operationalState_EndTime,,cycleFacility.CycleFacilityType.cycleFacility,cycleFacility,
    -> StringReplacer
Note: remove # from the / feature references
StringReplacer
    CASE = no
    FIND_TEXT = #
    NO_MATCH = _FME_NO_OP_
    REGEXP = no
    SRC_ATTRS = endNode,startNode
    -> AttributeSplitter
Note: The attribute value for "directionality" is held as a / URL therefore to extract the value from the URL / the attribute needs splitting after every "/". This / action will create a list. The values after the last / "/" will contain the attribute value.
AttributeSplitter
    ATTR_NAME = directionality.xlink_href
    DELIMITER = /
    DROP_EMPTY_PARTS = No
    LIST_NAME = directinality_list
    TRIM_OPTION = Both
    -> AttributeRenamer_4
Note: Renaming the last list produced by the AttributeSplitter / which holds the attribute value for the "directionality" attribute.
AttributeRenamer_4
    ATTR_LIST = directinality_list{5},directionality,
    -> AttributeRenamer_4_OUTPUT
Note: AttributeManager : Input
AttributeRenamer_4_OUTPUT: Junction
    -> AttributeManager_2
Note: AttributeRenamer_4 : Output
AttributeManager_2: Junction
    -> AttributeManager
Note: roadWidths and elevationgain
AttributeManager
    ATTR_TABLE:
      RENAME_SET_VALUE roadName1 > roadName1_Name
      RENAME_SET_VALUE roadName2 > roadName2_Name
      SET_TO roadWidthAverage = @Value(roadWidth.RoadWidthType.averageWidth)@Value(roadWidth.RoadWidthType.averageWidth.uom)
      SET_TO roadWidthMinimum = @Value(roadWidth.RoadWidthType.minimumWidth)@Value(roadWidth.RoadWidthType.minimumWidth.uom)
      SET_TO elevationGainInDirection = @Value(elevationGain.ElevationGainType.inDirection)@Value(elevationGain.ElevationGainType.inDirection.uom)
      SET_TO elevationGainOppositeDirection = @Value(elevationGain.ElevationGainType.inOppositeDirection)@Value(elevationGain.ElevationGainType.inOppositeDirection.uom)
    -> AttributeRenamer_11
    -> AttributeManager_OUTPUT
AttributeRenamer_11
    ATTR_TABLE:
      RENAME_SET_DEFAULT alternateIdentifier{0}.ThematicIdentifier.identifier > alternateIdentifier1
      RENAME_SET_DEFAULT alternateIdentifier{1}.ThematicIdentifier.identifier > alternateIdentifier2
      RENAME_SET_DEFAULT alternateIdentifier{2}.ThematicIdentifier.identifier > alternateIdentifier3
      RENAME_SET_DEFAULT alternateIdentifier{3}.ThematicIdentifier.identifier > alternateIdentifier4
      RENAME_SET_DEFAULT alternateIdentifier{4}.ThematicIdentifier.identifier > alternateIdentifier5
    -> AttributeCreator_4
Note: Red arrow indicates attribute currently not populated
RoadLink (writer GEOPACKAGE_1)
    attributes: TOID text(20), identifier text(16), identifierVersionId text(20), fictitious boolean, roadClassification text(21),indexed, routeHierarchy text(32), formOfWay text(42), trunkRoad boolean, primaryRoute boolean, roadClassificationNumber text(10), roadName1_Name text(255), roadName2_Name text(255), roadName1_Language text(3), roadName2_Language text(3), operationalState text(19), provenance text(40), directionality text(21), length double, matchStatus text(39), alternateIdentifier1 text(20), alternateIdentifier2 text(20), alternateIdentifier3 text(20), alternateIdentifier4 text(20), alternateIdentifier5 text(20), alternateIdentifier6 text(20), alternateIdentifier7 text(20), alternateIdentifier8 text(20), alternateIdentifier9 text(20), startGradeSeparation mediumint, endGradeSeparation mediumint,
      roadStructure text(14), cycleFacility text(120), cycleFacilityWholeLink text(1), roadWidthMinimum text(20), roadWidthAverage text(20), elevationGainInDirection text(20), elevationGainOppositeDirection text(20), startNode text(20), endNode text(20), alternativeName1 text(255), alternativeName2 text(255), alternativeName1_Language text(3), alternativeName2_Language text(3), beginLifespanVersion text(20), reasonForChange text(32), validFrom text(20), chunkname text(50)
Note: ListExploder_4 : Input
AttributeManager_OUTPUT: Junction
    -> ListExploder_5
Note: AttributeManager : Output
ListExploder_5: Junction
    -> ListExploder_4
RoadLink_NumberOfLanes (writer GEOPACKAGE_1)
    attributes: TOID text(20), direction text(50), minMaxNumberOfLanes text(20), numberOfLanes mediumint

Bookmark: miso addition
AttributeCreator_4
    ATTR_TABLE = SET_TO cycleFacilityWholeLink = FME_CONDITIONAL:DEFAULT_VALUE'_FME_NO_OP_'BOOL_OP;OR;COMPOSITE_TEST;<Unused>;TEST @Value(cycleFacility.CycleFacilityType.wholeLink) = true'T'BOOL_OP;OR;COMPOSITE_TEST;<Unused>;TEST @Value(cycleFacility.CycleFacilityType.wholeLink) = false'F'BOOL_OP;OR;COMPOSITE_TEST;<Unused>;TEST @Value(cycleFacility.CycleFacilityType.wholeLink.nilReason) = unknown'?'FME_NUM_CONDITIONS4___
    -> AttributeRenamer_12
AttributeRenamer_12
    ATTR_TABLE:
      RENAME_SET_DEFAULT alternateIdentifier{5}.ThematicIdentifier.identifier > alternateIdentifier6
      RENAME_SET_DEFAULT alternateIdentifier{6}.ThematicIdentifier.identifier > alternateIdentifier7
      RENAME_SET_DEFAULT alternateIdentifier{7}.ThematicIdentifier.identifier > alternateIdentifier8
      RENAME_SET_DEFAULT alternateIdentifier{8}.ThematicIdentifier.identifier > alternateIdentifier9
    -> RoadLink (writer GEOPACKAGE_1)

Bookmark: Create numberOfLanes reference table
ListExploder_4
    ATTR_ACCUM_MODE = Merge Incoming List
    ATTR_CONFLICT_RES = Use Incoming List
    INDEX_ATTR = _element_index
    LIST_ATTR = numberOfLanes{}
    ELEMENTS -> AttributeManager_3
AttributeManager_3
    ATTR_TABLE:
      REMOVE alternateIdentifier{}.ThematicIdentifier.identifier
      REMOVE alternateIdentifier{}.ThematicIdentifier.identifierScheme
      REMOVE alternateName{}
      REMOVE beginLifespanVersion
      REMOVE cycleFacility
      REMOVE cycleFacility.CycleFacilityType.cycleFacility.codeSpace
      REMOVE cycleFacility.CycleFacilityType.wholeLink
      REMOVE cycleFacility.CycleFacilityType.wholeLink.nilReason
      REMOVE directionality.owns
      REMOVE directionality.xlink_href
      REMOVE elevationGain.ElevationGainType.inDirection
      REMOVE elevationGain.ElevationGainType.inDirection.uom
      REMOVE elevationGain.ElevationGainType.inOppositeDirection
      REMOVE elevationGain.ElevationGainType.inOppositeDirection.uom
      REMOVE endGradeSeparation
      REMOVE endNode.owns
      REMOVE endNode
      REMOVE fictitious
      REMOVE formOfWay
      REMOVE formsPartOf{}.owns
      REMOVE formsPartOf{}.xlink_href
      REMOVE inNetwork{}.owns
      REMOVE inNetwork{}.xlink_href
      REMOVE localId
      REMOVE identifierNamespace
      REMOVE length
      REMOVE length.uom
      REMOVE matchStatus
      REMOVE matchStatus.codeSpace
      REMOVE NumberOfLanesType.direction.owns
      RENAME_SET_VALUE NumberOfLanesType.direction.xlink_href > direction
      RENAME_SET_VALUE NumberOfLanesType.minMaxNumberOfLanes > minMaxNumberOfLanes
      RENAME_SET_VALUE NumberOfLanesType.numberOfLanes > numberOfLanes
      REMOVE operationalState
      REMOVE operationalState.codeSpace
      REMOVE primaryRoute
      REMOVE provenance
      REMOVE provenance.codeSpace
      REMOVE reasonForChange
      REMOVE reasonForChange.codeSpace
      REMOVE relatedRoadArea{}.owns
      REMOVE relatedRoadArea{}.xlink_href
      REMOVE roadClassification
      REMOVE roadClassification.codeSpace
      REMOVE roadClassificationNumber
      REMOVE roadName{}
      REMOVE roadWidth.RoadWidthType.averageWidth
      REMOVE roadWidth.RoadWidthType.averageWidth.uom
      REMOVE roadWidth.RoadWidthType.confidenceLevel
      REMOVE roadWidth.RoadWidthType.minimumWidth
      REMOVE roadWidth.RoadWidthType.minimumWidth.uom
      REMOVE routeHierarchy
      REMOVE routeHierarchy.codeSpace
      REMOVE startGradeSeparation
      REMOVE startNode.owns
      REMOVE startNode
      REMOVE trunkRoad
      REMOVE validFrom
      REMOVE validFrom.nilReason
      REMOVE validFrom.xsi_nil
      REMOVE xml_ns_uri
      REMOVE roadName1_Language
      REMOVE roadName2_Language
      REMOVE alternativeName1
      REMOVE alternativeName1_Language
      REMOVE alternativeName2
      REMOVE alternativeName2_Language
      REMOVE operationsState_Reason
      REMOVE operationalState_EndTime
      REMOVE identifierVersionId
      REMOVE operationalState_State
      REMOVE operationalState_StartTime
      REMOVE roadWidthAverage
      REMOVE roadWidthMinimum
      REMOVE directinality_list{}
      REMOVE directionality
      REMOVE elevationGainInDirection
      REMOVE elevationGainOppositeDirection
      REMOVE _element_index
      REMOVE roadName1_Name
      REMOVE roadName2_Name
    -> StringReplacer_4
StringReplacer_4
    CASE = NO
    FIND_TEXT = http://inspire.ec.europa.eu/codelist/LinkDirectionValue/
    NO_MATCH = _FME_NO_OP_
    REGEXP = NO
    SRC_ATTRS = direction
    -> RoadLink_NumberOfLanes (writer GEOPACKAGE_1)

Bookmark: Identifies the "alternateIdentifier" (this will be an ESU identifier) for each RoadLink where it has been matched to the NSG
ListExploder
    ATTR_ACCUM_MODE = Merge Incoming List
    ATTR_CONFLICT_RES = Use Original
    INDEX_ATTR = _element_index
    LIST_ATTR = alternateIdentifier{}
    LIST_FOUND -> AttributeRenamer_8
AttributeRenamer_8
    ATTR_LIST = ThematicIdentifier.identifier,alternateIdentifier,,ThematicIdentifier.identifierScheme,alternateIdentifierSchema,
    -> RoadLink_AlternateIdentifier (writer GEOPACKAGE_1)
RoadLink_AlternateIdentifier (writer GEOPACKAGE_1)
    attributes: TOID text(20), alternateIdentifier text(20), alternateIdentifierSchema text(50)

Bookmark: Forms Part Of - Identifes which Road and Street features the RoadLink forms a part of.
ListExploder_2
    ATTR_ACCUM_MODE = Merge Incoming List
    ATTR_CONFLICT_RES = Use Original
    INDEX_ATTR = _element_index
    LIST_ATTR = formsPartOf{}
    LIST_FOUND -> TestFilter
Note: Test for whetherthe reference isto a / Road (osgb) or a Street (USRN)
TestFilter
    DEFAULT_VALUE = <UNFILTERED>
    TEST_LIST = BOOL_OP,OR,COMPOSITE_TEST,<Unused>,TEST_CLAUSE,"TEST @Value(xlink_href) CONTAINS #osgb",osgb,BOOL_OP,OR,COMPOSITE_TEST,<Unused>,TEST_CLAUSE,"TEST @Value(xlink_href) CONTAINS #usrn",usrn
    osgb -> AttributeCreator
    usrn -> AttributeCreator_2
    <UNFILTERED> -> AttributeCreator_3
AttributeCreator
    ATTR_LIST = refType,Road
    -> AttributeRenamer_9
AttributeCreator_2
    ATTR_LIST = refType,Street
    -> AttributeRenamer_9
AttributeCreator_3
    ATTR_LIST = refType,Other
    -> AttributeRenamer_9
AttributeRenamer_9
    ATTR_LIST = xlink_href,formsPartOf,
    -> StringReplacer_2
Note: remove # from the / feature references
StringReplacer_2
    CASE = no
    FIND_TEXT = #
    NO_MATCH = _FME_NO_OP_
    REGEXP = no
    SRC_ATTRS = formsPartOf
    -> RoadLink_FormsPartOf (writer GEOPACKAGE_1)
RoadLink_FormsPartOf (writer GEOPACKAGE_1)
    attributes: TOID text(20), formsPartOf text(20), refType text(20)

Bookmark: The OS MasterMap Topography Layer TOID reference that the RoadLink sits within
ListExploder_3
    ATTR_ACCUM_MODE = Merge Incoming List
    ATTR_CONFLICT_RES = Use Original
    INDEX_ATTR = _element_index
    LIST_ATTR = relatedRoadArea{}
    LIST_FOUND -> AttributeRenamer_10
AttributeRenamer_10
    ATTR_LIST = xlink_href,RelatedRoadAreaTOID,
    -> StringReplacer_3
Note: remove # from the / feature references
StringReplacer_3
    CASE = no
    FIND_TEXT = #
    NO_MATCH = _FME_NO_OP_
    REGEXP = no
    SRC_ATTRS = RelatedRoadAreaTOID
    -> RoadLink_TopoTOIDRef (writer GEOPACKAGE_1)
RoadLink_TopoTOIDRef (writer GEOPACKAGE_1)
    attributes: TOID text(20), RelatedRoadAreaTOID text(39)
