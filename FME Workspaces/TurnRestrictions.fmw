FME workspace TurnRestrictions.fmw

Parameters:
- SourceDataset_RoadLink = $(ROADS_DATA_INPUT_FOLDER)\Highways_Rrami_RoadLink_FULL_*.gml*   # Source RoadLink GML File(s)
- SourceDataset_TurnRestriction = $(ROADS_DATA_INPUT_FOLDER)\Highways_Rrami_TurnRestriction_FULL_*.gml*   # Source TurnRestriction GML File(s)
- DestDataset_GEOPACKAGE = $(MIDDLE_FOLDER)\TurnRestriction.gpkg   # Middle TurnRestriction Geopackage File

Readers:
- GML_1: GML from $(SourceDataset_RoadLink)
- GML_2: GML from $(SourceDataset_TurnRestriction)

Writers:
- GEOPACKAGE_1: GEOPACKAGE to $(DestDataset_GEOPACKAGE)
- GEOPACKAGE_2: GEOPACKAGE to $(DestDataset_GEOPACKAGE)

Note: Change to local input
TurnRestriction (reader GML_2)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NodeReference.element.owns xml_boolean, networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer,
      networkRef{}.LinkReference.applicableDirection.xsi_nil xml_boolean, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64, networkRef{}.SimpleLinearReference.offset.nilReason xml_buffer, networkRef{}.SimpleLinearReference.offset.uom xml_buffer, networkRef{}.SimpleLinearReference.offset.xsi_nil xml_boolean, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean, networkRef{}.SimplePointReference.atPosition xml_real64, networkRef{}.SimplePointReference.atPosition.uom xml_buffer, networkRef{}.SimplePointReference.offset xml_real64,
      networkRef{}.SimplePointReference.offset.nilReason xml_buffer, networkRef{}.SimplePointReference.offset.uom xml_buffer, networkRef{}.SimplePointReference.offset.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, restriction xml_buffer, restriction.codeSpace xml_buffer, inclusion.VehicleQualifier.vehicle{} xml_buffer, inclusion.VehicleQualifier.vehicle{}.codeSpace xml_buffer, inclusion.VehicleQualifier.use{} xml_buffer, inclusion.VehicleQualifier.use{}.codeSpace xml_buffer, inclusion.VehicleQualifier.load{} xml_buffer, inclusion.VehicleQualifier.load{}.codeSpace xml_buffer, exemption.VehicleQualifier.vehicle{} xml_buffer, exemption.VehicleQualifier.vehicle{}.codeSpace xml_buffer,
      exemption.VehicleQualifier.use{} xml_buffer, exemption.VehicleQualifier.use{}.codeSpace xml_buffer, exemption.VehicleQualifier.load{} xml_buffer, exemption.VehicleQualifier.load{}.codeSpace xml_buffer, timeInterval{}.TemporalPropertyType.namedDate{} xml_buffer, timeInterval{}.TemporalPropertyType.namedDate{}.codeSpace xml_buffer, timeInterval{}.TemporalPropertyType.dateRange{}.DateRangeType.startDate xml_date, timeInterval{}.TemporalPropertyType.dateRange{}.DateRangeType.endDate xml_date, timeInterval{}.TemporalPropertyType.dateRange{}.DateRangeType.startMonthDay xml_buffer, timeInterval{}.TemporalPropertyType.dateRange{}.DateRangeType.endMonthDay xml_buffer, timeInterval{}.TemporalPropertyType.dayPeriod{}.DayPropertyType.namedDay{} xml_buffer, timeInterval{}.TemporalPropertyType.dayPeriod{}.DayPropertyType.namedDay{}.codeSpace xml_buffer, timeInterval{}.TemporalPropertyType.dayPeriod{}.DayPropertyType.namedPeriod{} xml_buffer, timeInterval{}.TemporalPropertyType.dayPeriod{}.DayPropertyType.namedPeriod{}.codeSpace xml_buffer, timeInterval{}.TemporalPropertyType.dayPeriod{}.DayPropertyType.timePeriod{}.TimePropertyType.namedTime{} xml_buffer, timeInterval{}.TemporalPropertyType.dayPeriod{}.DayPropertyType.timePeriod{}.TimePropertyType.namedTime{}.codeSpace xml_buffer, timeInterval{}.TemporalPropertyType.dayPeriod{}.DayPropertyType.timePeriod{}.TimePropertyType.timeRange{}.TimeRangeType.startTime xml_time, timeInterval{}.TemporalPropertyType.dayPeriod{}.DayPropertyType.timePeriod{}.TimePropertyType.timeRange{}.TimeRangeType.endTime xml_time, reasonForChange xml_buffer, reasonForChange.codeSpace xml_buffer
    -> AttributeRenamer
Note: Rename attributes
AttributeRenamer
    ATTR_LIST = inspireId.Identifier.versionId,versionId,,inspireId.Identifier.localId,identifier,,gml_id,TOID,,fme_basename,chunkname,
    -> ListExploder_4
    -> ListExploder_5
    -> ListExploder_9
    -> ListExploder_7
    -> ListExploder_3
    -> ListExploder_2
    -> ListExploder_6
    -> TestFilter_2
ListExploder_6
    ATTR_ACCUM_MODE = Merge Incoming List
    ATTR_CONFLICT_RES = Use Original
    INDEX_ATTR = _element_index
    LIST_ATTR = timeInterval{}
    LIST_FOUND -> AttributeRenamer_6
AttributeRenamer_6
    ATTR_LIST = id,parentFeature_ID,
    -> Counter
Counter
    CNT_ATTR = timeInterval_ID
    DOMAIN = counter
    SCOPE = Global
    START = 0
    -> ListExploder_8
    -> TQ_Parent_Date_Join (writer GEOPACKAGE_1)
    -> ListExploder_10
    -> ListExploder_11
TQ_Parent_Date_Join (writer GEOPACKAGE_1)
    attributes: parentFeature_ID text(50), timeInterval_ID mediumint
ListExploder_11
    ATTR_ACCUM_MODE = Merge Incoming List
    ATTR_CONFLICT_RES = Use Original
    INDEX_ATTR = _element_index
    LIST_ATTR = TemporalPropertyType.dayPeriod{}
    LIST_FOUND -> Counter_2
Counter_2
    CNT_ATTR = dayPeriod_ID
    DOMAIN = counter
    SCOPE = Global
    START = 0
    -> ListExploder_12
    -> ListExploder_13
    -> ListExploder_14
    -> TQ_Date_Day_Join (writer GEOPACKAGE_1)
TQ_Date_Day_Join (writer GEOPACKAGE_1)
    attributes: parentFeature_ID text(50), timeInterval_ID mediumint, dayPeriod_ID mediumint
ListExploder_14
    ATTR_ACCUM_MODE = Merge Incoming List
    ATTR_CONFLICT_RES = Use Original
    INDEX_ATTR = _element_index
    LIST_ATTR = DayPropertyType.timePeriod{}
    LIST_FOUND -> Counter_3
Counter_3
    CNT_ATTR = timePeriod_ID
    DOMAIN = counter
    SCOPE = Global
    START = 0
    -> ListExploder_15
    -> ListExploder_16
    -> TQ_Day_Time_Join (writer GEOPACKAGE_1)
TQ_Day_Time_Join (writer GEOPACKAGE_1)
    attributes: parentFeature_ID text(50), timeInterval_ID mediumint, dayPeriod_ID mediumint, timePeriod_ID mediumint

Bookmark: miso addition
TestFilter_2
    DEFAULT_VALUE = <UNFILTERED>
    TEST_LIST = "BOOL_OP,OR,COMPOSITE_TEST,""""""<Unused>"""""",TEST_CLAUSE,TEST validFrom ATTRIBUTE_HAS_A_VALUE """,ValidFrom
    ValidFrom -> DateFormatter_3
    <UNFILTERED> -> DateFormatter
DateFormatter_3
    DATE_ATTR = validFrom
    FMT = FME Date (%Y%m%d)
    INVALID_DATE_VALUE = _FME_NO_OP_
    SRCFMT = Unknown - Automatic Detection
    -> DateFormatter

Bookmark: Create TurnRestriction feature
Note: This is an example output, writer will need to be added for specific output
Note: Format dates as DMY
DateFormatter
    DATE_ATTR = beginLifespanVersion,endLifespanVersion
    FMT = FME Date (%Y%m%d)
    INVALID_DATE_VALUE = FME_NULL_VALUE
    SRCFMT = Unknown - Automatic Detection
    -> ListElementCounter

Bookmark: miso addition
ListElementCounter
    CNT_ATTR = NoOfNetworkLinks
    LIST_NAME = networkRef{}
    -> ListConcatenator_7
ListConcatenator_7
    DROP_EMPTY_PARTS = No
    LIST_ATTR = networkRef{}.LinkReference.applicableDirection.xlink_href
    SEP = ,
    VAL_ATTR = DirectionChain
    -> ListConcatenator_8
ListConcatenator_8
    DROP_EMPTY_PARTS = No
    LIST_ATTR = networkRef{}.LinkReference.element.xlink_href
    SEP = ,
    VAL_ATTR = LinkTOIDChain
    -> AttributeCreator_29
AttributeCreator_29
    ATTR_TABLE:
      SET_TO ChainOfNetworkLinks = FME_CONDITIONAL:DEFAULT_VALUE'_FME_NO_OP_'BOOL_OP;AND;COMPOSITE_TEST;<Unused>;TEST @Value(NoOfNetworkLinks) > 0;TEST @Substring(@Value(DirectionChain),@FindString(@Value(DirectionChain),"LinkDirectionValue/")+19,11) = inDirection'1+@Substring(@Value(LinkTOIDChain),1,20)'BOOL_OP;OR;COMPOSITE_TEST;<Unused>;TEST @Value(NoOfNetworkLinks) > 0'1-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_30
AttributeCreator_30
    ATTR_TABLE:
      SET_TO ChainOfNetworkLinks = FME_CONDITIONAL:DEFAULT_VALUE'_FME_NO_OP_'BOOL_OP;AND;COMPOSITE_TEST;<Unused>;TEST @Value(NoOfNetworkLinks) > 1;TEST @Substring(@Value(DirectionChain),@FindString(@Value(DirectionChain),"LinkDirectionValue/")+19,11) = inDirection'@Value(ChainOfNetworkLinks), 2+@Substring(@Value(LinkTOIDChain),1,20)'BOOL_OP;OR;COMPOSITE_TEST;<Unused>;TEST @Value(NoOfNetworkLinks) > 1'@Value(ChainOfNetworkLinks), 2-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_39
AttributeCreator_39
    ATTR_TABLE:
      SET_TO ChainOfNetworkLinks = FME_CONDITIONAL:DEFAULT_VALUE'_FME_NO_OP_'BOOL_OP;AND;COMPOSITE_TEST;<Unused>;TEST @Value(NoOfNetworkLinks) > 2;TEST @Substring(@Value(DirectionChain),@FindString(@Value(DirectionChain),"LinkDirectionValue/")+19,11) = inDirection'@Value(ChainOfNetworkLinks), 3+@Substring(@Value(LinkTOIDChain),1,20)'BOOL_OP;OR;COMPOSITE_TEST;<Unused>;TEST @Value(NoOfNetworkLinks) > 2'@Value(ChainOfNetworkLinks), 3-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_41
AttributeCreator_41
    ATTR_TABLE:
      SET_TO ChainOfNetworkLinks = FME_CONDITIONAL:DEFAULT_VALUE'_FME_NO_OP_'BOOL_OP;AND;COMPOSITE_TEST;<Unused>;TEST @Value(NoOfNetworkLinks) > 3;TEST @Substring(@Value(DirectionChain),@FindString(@Value(DirectionChain),"LinkDirectionValue/")+19,11) = inDirection'@Value(ChainOfNetworkLinks), 4+@Substring(@Value(LinkTOIDChain),1,20)'BOOL_OP;OR;COMPOSITE_TEST;<Unused>;TEST @Value(NoOfNetworkLinks) > 3'@Value(ChainOfNetworkLinks), 4-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_42
AttributeCreator_42
    ATTR_TABLE:
      SET_TO ChainOfNetworkLinks = FME_CONDITIONAL:DEFAULT_VALUE'_FME_NO_OP_'BOOL_OP;AND;COMPOSITE_TEST;<Unused>;TEST @Value(NoOfNetworkLinks) > 4;TEST @Substring(@Value(DirectionChain),@FindString(@Value(DirectionChain),"LinkDirectionValue/")+19,11) = inDirection'@Value(ChainOfNetworkLinks), 5+@Substring(@Value(LinkTOIDChain),1,20)'BOOL_OP;OR;COMPOSITE_TEST;<Unused>;TEST @Value(NoOfNetworkLinks) > 4'@Value(ChainOfNetworkLinks), 5-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_45
AttributeCreator_45
    ATTR_TABLE:
      SET_TO ChainOfNetworkLinks = FME_CONDITIONAL:DEFAULT_VALUE'_FME_NO_OP_'BOOL_OP;AND;COMPOSITE_TEST;<Unused>;TEST @Value(NoOfNetworkLinks) > 5;TEST @Substring(@Value(DirectionChain),@FindString(@Value(DirectionChain),"LinkDirectionValue/")+19,11) = inDirection'@Value(ChainOfNetworkLinks), 6+@Substring(@Value(LinkTOIDChain),1,20)'BOOL_OP;OR;COMPOSITE_TEST;<Unused>;TEST @Value(NoOfNetworkLinks) > 5'@Value(ChainOfNetworkLinks), 6-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_47
AttributeCreator_47
    ATTR_TABLE:
      SET_TO ChainOfNetworkLinks = FME_CONDITIONAL:DEFAULT_VALUE'_FME_NO_OP_'BOOL_OP;AND;COMPOSITE_TEST;<Unused>;TEST @Value(NoOfNetworkLinks) > 6;TEST @Substring(@Value(DirectionChain),@FindString(@Value(DirectionChain),"LinkDirectionValue/")+19,11) = inDirection'@Value(ChainOfNetworkLinks), 7+@Substring(@Value(LinkTOIDChain),1,20)'BOOL_OP;OR;COMPOSITE_TEST;<Unused>;TEST @Value(NoOfNetworkLinks) > 6'@Value(ChainOfNetworkLinks), 7-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_48
AttributeCreator_48
    ATTR_TABLE:
      SET_TO ChainOfNetworkLinks = FME_CONDITIONAL:DEFAULT_VALUE'_FME_NO_OP_'BOOL_OP;AND;COMPOSITE_TEST;<Unused>;TEST @Value(NoOfNetworkLinks) > 7;TEST @Substring(@Value(DirectionChain),@FindString(@Value(DirectionChain),"LinkDirectionValue/")+19,11) = inDirection'@Value(ChainOfNetworkLinks), 8+@Substring(@Value(LinkTOIDChain),1,20)'BOOL_OP;OR;COMPOSITE_TEST;<Unused>;TEST @Value(NoOfNetworkLinks) > 7'@Value(ChainOfNetworkLinks), 8-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> ListExploder

Bookmark: Indicates the RoadLink the TurnRestriction references
ListExploder
    ATTR_ACCUM_MODE = Merge Incoming List
    ATTR_CONFLICT_RES = Use Original
    INDEX_ATTR = _element_index
    LIST_ATTR = networkRef{}
    LIST_FOUND -> AttributeRenamer_2
AttributeRenamer_2
    ATTR_LIST = LinkReference.element.xlink_href,RoadLink_TOID,,_element_index,sequence,
    -> AttributeSplitter
Note: The attribute value for "directionality" is held as a / URL therefore to extract the value from the URL / the attribute needs splitting after every "/". This / action will create a list. The values after the last / "/" will contain the attribute value.
AttributeSplitter
    ATTR_NAME = LinkReference.applicableDirection.xlink_href
    DELIMITER = /
    DROP_EMPTY_PARTS = No
    LIST_NAME = _list
    TRIM_OPTION = Both
    -> AttributeRenamer_11
Note: Renaming the last list produced by the / AttributeSplitter which holds the attribute / value for the "directionality" attribute.
AttributeRenamer_11
    ATTR_LIST = _list{5},applicableDirection,
    -> StringReplacer
Note: remove # from the / feature references
StringReplacer
    CASE = no
    FIND_TEXT = #
    NO_MATCH = _FME_NO_OP_
    REGEXP = no
    SRC_ATTRS = RoadLink_TOID
    -> TurnRestriction_NetworkRef (writer GEOPACKAGE_1)
    -> ListConcatenator
TurnRestriction_NetworkRef (writer GEOPACKAGE_1)
    attributes: TOID text(20), RoadLink_TOID text(20), applicableDirection text(120), sequence mediumint

Bookmark: Concatenate inclusion & exemption
ListConcatenator
    DROP_EMPTY_PARTS = Yes
    LIST_ATTR = inclusion.VehicleQualifier.vehicle{}
    SEP = ", "
    VAL_ATTR = Inclusion_Vehicle
    -> ListConcatenator_2
ListConcatenator_2
    DROP_EMPTY_PARTS = Yes
    LIST_ATTR = inclusion.VehicleQualifier.use{}
    SEP = ", "
    VAL_ATTR = Inclusion_Use
    -> ListConcatenator_3
ListConcatenator_3
    DROP_EMPTY_PARTS = Yes
    LIST_ATTR = inclusion.VehicleQualifier.load{}
    SEP = ", "
    VAL_ATTR = Inclusion_Load
    -> AttributeCreator_14
AttributeCreator_14
    ATTR_TABLE = SET_TO Inclusion = FME_CONDITIONAL:DEFAULT_VALUE'_FME_NO_OP_'BOOL_OP;AND;COMPOSITE_TEST;<Unused>;TEST Inclusion_Vehicle ATTRIBUTE_HAS_A_VALUE _FME_BLANK_STRING_;TEST Inclusion_Use ATTRIBUTE_HAS_A_VALUE _FME_BLANK_STRING_;TEST Inclusion_Load ATTRIBUTE_HAS_A_VALUE _FME_BLANK_STRING_'Applying to: @Value(Inclusion_Vehicle), @Value(Inclusion_Use), @Value(Inclusion_Load)'BOOL_OP;AND;COMPOSITE_TEST;<Unused>;TEST Inclusion_Vehicle ATTRIBUTE_HAS_A_VALUE _FME_BLANK_STRING_;TEST Inclusion_Use ATTRIBUTE_HAS_A_VALUE _FME_BLANK_STRING_'Applying to: @Value(Inclusion_Vehicle), @Value(Inclusion_Use)'BOOL_OP;AND;COMPOSITE_TEST;<Unused>;TEST Inclusion_Vehicle ATTRIBUTE_HAS_A_VALUE _FME_BLANK_STRING_;TEST Inclusion_Load ATTRIBUTE_HAS_A_VALUE _FME_BLANK_STRING_'Applying to: @Value(Inclusion_Vehicle), @Value(Inclusion_Load)'BOOL_OP;AND;COMPOSITE_TEST;<Unused>;TEST Inclusion_Use ATTRIBUTE_HAS_A_VALUE _FME_BLANK_STRING_;TEST Inclusion_Load ATTRIBUTE_HAS_A_VALUE _FME_BLANK_STRING_'Applying to: @Value(Inclusion_Use), @Value(Inclusion_Load)'BOOL_OP;OR;COMPOSITE_TEST;<Unused>;TEST Inclusion_Vehicle ATTRIBUTE_HAS_A_VALUE _FME_BLANK_STRING_'Applying to: @Value(Inclusion_Vehicle)'BOOL_OP;OR;COMPOSITE_TEST;<Unused>;TEST Inclusion_Use ATTRIBUTE_HAS_A_VALUE _FME_BLANK_STRING_'Applying to: @Value(Inclusion_Use)'BOOL_OP;OR;COMPOSITE_TEST;<Unused>;TEST Inclusion_Load ATTRIBUTE_HAS_A_VALUE _FME_BLANK_STRING_'Applying to: @Value(Inclusion_Load)'FME_NUM_CONDITIONS8___
    -> ListConcatenator_4
ListConcatenator_4
    DROP_EMPTY_PARTS = Yes
    LIST_ATTR = exemption.VehicleQualifier.vehicle{}
    SEP = ", "
    VAL_ATTR = Exemption_Vehicle
    -> ListConcatenator_5
ListConcatenator_5
    DROP_EMPTY_PARTS = Yes
    LIST_ATTR = exemption.VehicleQualifier.use{}
    SEP = ", "
    VAL_ATTR = Exemption_Use
    -> ListConcatenator_6
ListConcatenator_6
    DROP_EMPTY_PARTS = Yes
    LIST_ATTR = exemption.VehicleQualifier.load{}
    SEP = ", "
    VAL_ATTR = Exemption_Load
    -> AttributeCreator_15
AttributeCreator_15
    ATTR_TABLE = SET_TO Exemption = FME_CONDITIONAL:DEFAULT_VALUE'_FME_NO_OP_'BOOL_OP;AND;COMPOSITE_TEST;<Unused>;TEST Exemption_Vehicle ATTRIBUTE_HAS_A_VALUE _FME_BLANK_STRING_;TEST Exemption_Use ATTRIBUTE_HAS_A_VALUE _FME_BLANK_STRING_;TEST Exemption_Load ATTRIBUTE_HAS_A_VALUE _FME_BLANK_STRING_'Except for: @Value(Exemption_Vehicle), @Value(Exemption_Use), @Value(Exemption_Load)'BOOL_OP;AND;COMPOSITE_TEST;<Unused>;TEST Exemption_Vehicle ATTRIBUTE_HAS_A_VALUE _FME_BLANK_STRING_;TEST Exemption_Use ATTRIBUTE_HAS_A_VALUE _FME_BLANK_STRING_'Except for: @Value(Exemption_Vehicle), @Value(Exemption_Use)'BOOL_OP;AND;COMPOSITE_TEST;<Unused>;TEST Exemption_Vehicle ATTRIBUTE_HAS_A_VALUE _FME_BLANK_STRING_;TEST Exemption_Load ATTRIBUTE_HAS_A_VALUE _FME_BLANK_STRING_'Except for: @Value(Exemption_Vehicle), @Value(Exemption_Load)'BOOL_OP;AND;COMPOSITE_TEST;<Unused>;TEST Exemption_Use ATTRIBUTE_HAS_A_VALUE _FME_BLANK_STRING_;TEST Exemption_Load ATTRIBUTE_HAS_A_VALUE _FME_BLANK_STRING_'Except for: @Value(Exemption_Use), @Value(Exemption_Load)'BOOL_OP;OR;COMPOSITE_TEST;<Unused>;TEST Exemption_Vehicle ATTRIBUTE_HAS_A_VALUE _FME_BLANK_STRING_'Except for: @Value(Exemption_Vehicle)'BOOL_OP;OR;COMPOSITE_TEST;<Unused>;TEST Exemption_Use ATTRIBUTE_HAS_A_VALUE _FME_BLANK_STRING_'Except for: @Value(Exemption_Use)'BOOL_OP;OR;COMPOSITE_TEST;<Unused>;TEST Exemption_Load ATTRIBUTE_HAS_A_VALUE _FME_BLANK_STRING_'Except for: @Value(Exemption_Load)'FME_NUM_CONDITIONS8___
    -> AttributeKeeper

Bookmark: Add information from RoadLinks
AttributeKeeper
    KEEP_ATTRS = identifier,beginLifespanVersion,applicableDirection,Exemption,TOID,sequence,RoadLink_TOID,validFrom,validTo,versionId,ChainOfNetworkLinks,reasonForChange,Inclusion,chunkname,restriction,NoOfNetworkLinks,endLifespanVersion
    KEEP_LIST = exemption.VehicleQualifier.load{} exemption.VehicleQualifier.load{}.codeSpace exemption.VehicleQualifier.use{} exemption.VehicleQualifier.use{}.codeSpace exemption.VehicleQualifier.vehicle{} exemption.VehicleQualifier.vehicle{}.codeSpace inclusion.VehicleQualifier.load{}.codeSpace inclusion.VehicleQualifier.use{}.codeSpace inclusion.VehicleQualifier.vehicle{}.codeSpace
    -> FeatureJoiner [LEFT]
RoadLink (reader GML_1)
    attributes: alternateIdentifier{}.ThematicIdentifier.identifier xml_char(20), alternateIdentifier{}.ThematicIdentifier.identifierScheme xml_char(39), alternateName{} xml_char(24), beginLifespanVersion xml_char(24), cycleFacility.CycleFacilityType.cycleFacility xml_char(39), cycleFacility.CycleFacilityType.cycleFacility.codeSpace xml_char(62), cycleFacility.CycleFacilityType.wholeLink xml_char(1), cycleFacility.CycleFacilityType.wholeLink.nilReason xml_char(8), cycleFacility.CycleFacilityType.wholeLink.xsi_nil xml_char(5), directionality.owns xml_char(6), directionality.xlink_href xml_char(76), elevationGain.ElevationGainType.inDirection xml_decimal(4,0), elevationGain.ElevationGainType.inDirection.uom xml_char(2), elevationGain.ElevationGainType.inOppositeDirection xml_decimal(4,0), elevationGain.ElevationGainType.inOppositeDirection.uom xml_char(2), endGradeSeparation xml_decimal(2,0), endNode.owns xml_char(6), endNode.xlink_href xml_char(22), fictitious xml_char(6), formOfWay xml_char(32), formsPartOf{}.owns xml_char(6), formsPartOf{}.xlink_href xml_char(22), inNetwork{}.owns xml_char(6), inNetwork{}.xlink_href xml_char(18), inspireId.Identifier.localId xml_decimal(17,0), inspireId.Identifier.namespace xml_char(19), length xml_decimal(7,2), length.uom xml_char(2), matchStatus xml_char(26), matchStatus.codeSpace xml_char(61),
      numberOfLanes{}.NumberOfLanesType.direction.owns xml_char(6), numberOfLanes{}.NumberOfLanesType.direction.xlink_href xml_char(76), numberOfLanes{}.NumberOfLanesType.minMaxNumberOfLanes xml_char(8), numberOfLanes{}.NumberOfLanesType.numberOfLanes xml_decimal(2,0), operationalState xml_char(5), operationalState.codeSpace xml_char(66), primaryRoute xml_char(6), provenance xml_char(16), provenance.codeSpace xml_char(66), reasonForChange xml_char(4), reasonForChange.codeSpace xml_char(47), relatedRoadArea{}.owns xml_char(6), relatedRoadArea{}.xlink_href xml_char(22), roadClassification xml_char(22), roadClassification.codeSpace xml_char(59), roadClassificationNumber xml_char(6), roadName{} xml_char(37), roadWidth.RoadWidthType.averageWidth xml_decimal(3,0), roadWidth.RoadWidthType.averageWidth.uom xml_char(2), roadWidth.RoadWidthType.confidenceLevel xml_decimal(2,0), roadWidth.RoadWidthType.minimumWidth xml_decimal(3,0), roadWidth.RoadWidthType.minimumWidth.uom xml_char(2), routeHierarchy xml_char(33), routeHierarchy.codeSpace xml_char(53), startGradeSeparation xml_decimal(2,0), startNode.owns xml_char(6), startNode.xlink_href xml_char(22), trunkRoad xml_char(6), validFrom xml_char(1), validFrom.nilReason xml_char(8),
      validFrom.xsi_nil xml_char(5), roadStructure xml_char(15)
    -> FeatureJoiner [RIGHT]
FeatureJoiner
    ATTR_CONFLICT_RES = Use Left
    GEOMETRY_HANDLING = Use Right
    JOIN_KEYS = RoadLink_TOID gml_id AUTO
    JOIN_MODE = Inner
    JOINED -> AttributeRenamer_25

Bookmark: vehicleQualifer.use values have been exposed
ListExploder_4
    ATTR_ACCUM_MODE = Merge Incoming List
    ATTR_CONFLICT_RES = Use Original
    INDEX_ATTR = _element_index
    LIST_ATTR = exemption.VehicleQualifier.use{}
    LIST_FOUND -> AttributeCreator_2
AttributeCreator_2
    ATTR_LIST = exemptionType,use
    -> AttributeRenamer_4
AttributeRenamer_4
    ATTR_LIST = exemption.VehicleQualifier.use,exemption,
    -> TurnRestriction_Exemption (writer GEOPACKAGE_1)

Bookmark: vehicleQualifer.vehicle values have been exposed
ListExploder_5
    ATTR_ACCUM_MODE = Merge Incoming List
    ATTR_CONFLICT_RES = Use Original
    INDEX_ATTR = _element_index
    LIST_ATTR = exemption.VehicleQualifier.vehicle{}
    LIST_FOUND -> AttributeCreator_3
AttributeCreator_3
    ATTR_LIST = exemptionType,vehicle
    -> AttributeRenamer_5
AttributeRenamer_5
    ATTR_LIST = exemption.VehicleQualifier.vehicle,exemption,
    -> TurnRestriction_Exemption (writer GEOPACKAGE_1)

Bookmark: vehicleQualifer.load values have been exposed
ListExploder_3
    ATTR_ACCUM_MODE = Merge Incoming List
    ATTR_CONFLICT_RES = Use Original
    INDEX_ATTR = _element_index
    LIST_ATTR = exemption.VehicleQualifier.load{}
    LIST_FOUND -> AttributeCreator
AttributeCreator
    ATTR_LIST = exemptionType,load
    -> AttributeRenamer_3
AttributeRenamer_3
    ATTR_LIST = exemption.VehicleQualifier.load,exemption,
    -> TurnRestriction_Exemption (writer GEOPACKAGE_1)

Bookmark: Identifies the "exemption" "vehicleQualifer" attribute values which apply to any TurnRestriction
Note: The "exemption" attribute is populated by a vehicleQualifer data type. There are 3 attributes which contribute to the vehicleQualifer which are: / 1. Use / 2. Vehicle / 3. Load / Each of these 3 attributes have a multiplicity of 0..* so therefore need to be exposed to ensure all values populate the resulting table. This is carried out by the ListExploder transformer.
TurnRestriction_Exemption (writer GEOPACKAGE_1)
    attributes: TOID text(20), exemption text(50), exemptionType text(10)

Bookmark: vehicleQualifer.use values have been exposed
ListExploder_7
    ATTR_ACCUM_MODE = Merge Incoming List
    ATTR_CONFLICT_RES = Use Original
    INDEX_ATTR = _element_index
    LIST_ATTR = inclusion.VehicleQualifier.use{}
    LIST_FOUND -> AttributeCreator_5
AttributeCreator_5
    ATTR_LIST = inclusionType,use
    -> AttributeRenamer_9
AttributeRenamer_9
    ATTR_LIST = inclusion.VehicleQualifier.use,inclusion,
    -> TurnRestriction_inclusion (writer GEOPACKAGE_1)

Bookmark: vehicleQualifer.vehicle values have been exposed
ListExploder_9
    ATTR_ACCUM_MODE = Merge Incoming List
    ATTR_CONFLICT_RES = Use Original
    INDEX_ATTR = _element_index
    LIST_ATTR = inclusion.VehicleQualifier.vehicle{}
    LIST_FOUND -> AttributeCreator_6
AttributeCreator_6
    ATTR_LIST = inclusionType,vehicle
    -> AttributeRenamer_10
AttributeRenamer_10
    ATTR_LIST = inclusion.VehicleQualifier.vehicle,inclusion,
    -> TurnRestriction_inclusion (writer GEOPACKAGE_1)

Bookmark: vehicleQualifer.load values have been exposed
ListExploder_2
    ATTR_ACCUM_MODE = Merge Incoming List
    ATTR_CONFLICT_RES = Use Original
    INDEX_ATTR = _element_index
    LIST_ATTR = inclusion.VehicleQualifier.load{}
    LIST_FOUND -> AttributeCreator_4
AttributeCreator_4
    ATTR_LIST = inclusionType,load
    -> AttributeRenamer_8
AttributeRenamer_8
    ATTR_LIST = inclusion.VehicleQualifier.load,inclusion,
    -> TurnRestriction_inclusion (writer GEOPACKAGE_1)

Bookmark: Identifies the "inclusion" "vehicleQualifer" attribute values which apply to any TurnRestriction
Note: The "inclusion" attribute is populated by a vehicleQualifer data type. There are 3 attributes which contribute to the vehicleQualifer which are: / 1. Use / 2. Vehicle / 3. Load / Each of these 3 attributes have a multiplicity of 0..* so therefore need to be exposed to ensure all values populate the resulting table. This is carried out by the ListExploder transformer.
TurnRestriction_inclusion (writer GEOPACKAGE_1)
    attributes: TOID text(20), inclusion text(50), inclusionType text(10)

Bookmark: DateRange
ListExploder_8
    ATTR_ACCUM_MODE = Merge Incoming List
    ATTR_CONFLICT_RES = Use Original
    INDEX_ATTR = _element_index
    LIST_ATTR = TemporalPropertyType.dateRange{}
    LIST_FOUND -> AttributeRenamer_7
AttributeRenamer_7
    ATTR_LIST = DateRangeType.startDate,startDate,,DateRangeType.endDate,endDate,,DateRangeType.startMonthDay,startMonthDay,,DateRangeType.endMonthDay,endMonthDay,
    -> DateFormatter_2
DateFormatter_2
    DATE_ATTR = endDate,startDate
    FMT = FME Date (%Y%m%d)
    INVALID_DATE_VALUE = _FME_NO_OP_
    SRCFMT = Unknown - Automatic Detection
    -> TQ_DateRange (writer GEOPACKAGE_1)
TQ_DateRange (writer GEOPACKAGE_1)
    attributes: parentFeature_ID text(50), timeInterval_ID mediumint, startDate datetime, endDate datetime, startMonthDay text(10), endMonthDay text(10)

Bookmark: NamedDate
ListExploder_10
    ATTR_ACCUM_MODE = Merge Incoming List
    ATTR_CONFLICT_RES = Use Original
    INDEX_ATTR = _element_index
    LIST_ATTR = TemporalPropertyType.namedDate{}
    LIST_FOUND -> AttributeRenamer_12
AttributeRenamer_12
    ATTR_LIST = TemporalPropertyType.namedDate,namedDate,
    -> TQ_NamedDate (writer GEOPACKAGE_1)
TQ_NamedDate (writer GEOPACKAGE_1)
    attributes: parentFeature_ID text(50), timeInterval_ID mediumint, namedDate text(20)

Bookmark: NamedDay
ListExploder_12
    ATTR_ACCUM_MODE = Merge Incoming List
    ATTR_CONFLICT_RES = Use Original
    INDEX_ATTR = _element_index
    LIST_ATTR = DayPropertyType.namedDay{}
    LIST_FOUND -> AttributeRenamer_13
AttributeRenamer_13
    ATTR_LIST = DayPropertyType.namedDay,namedDay,
    -> TQ_NamedDay (writer GEOPACKAGE_1)
TQ_NamedDay (writer GEOPACKAGE_1)
    attributes: parentFeature_ID text(50), timeInterval_ID mediumint, dayPeriod_ID mediumint, namedDay text(50)

Bookmark: TimeRange
ListExploder_15
    ATTR_ACCUM_MODE = Merge Incoming List
    ATTR_CONFLICT_RES = Use Original
    INDEX_ATTR = _element_index
    LIST_ATTR = TimePropertyType.timeRange{}
    LIST_FOUND -> AttributeRenamer_15
AttributeRenamer_15
    ATTR_LIST = TimeRangeType.startTime,startTime,,TimeRangeType.endTime,endTime,
    -> TQ_TimeRange (writer GEOPACKAGE_1)
TQ_TimeRange (writer GEOPACKAGE_1)
    attributes: parentFeature_ID text(50), timeInterval_ID mediumint, dayPeriod_ID mediumint, timePeriod_ID mediumint, startTime text(10), endTime text(10)

Bookmark: NamedTime
ListExploder_16
    ATTR_ACCUM_MODE = Merge Incoming List
    ATTR_CONFLICT_RES = Use Original
    INDEX_ATTR = _element_index
    LIST_ATTR = TimePropertyType.namedTime{}
    LIST_FOUND -> AttributeRenamer_16
AttributeRenamer_16
    ATTR_LIST = TimePropertyType.namedTime,namedTime,
    -> TQ_NamedTime (writer GEOPACKAGE_1)
TQ_NamedTime (writer GEOPACKAGE_1)
    attributes: parentFeature_ID text(50), timeInterval_ID mediumint, dayPeriod_ID mediumint, timePeriod_ID mediumint, namedTime text(50)

Bookmark: NamedPeriod
ListExploder_13
    ATTR_ACCUM_MODE = Merge Incoming List
    ATTR_CONFLICT_RES = Use Original
    INDEX_ATTR = _element_index
    LIST_ATTR = DayPropertyType.namedPeriod{}
    LIST_FOUND -> AttributeRenamer_14
AttributeRenamer_14
    ATTR_LIST = DayPropertyType.namedPeriod,namedPeriod,
    -> TQ_NamedPeriod (writer GEOPACKAGE_1)
TQ_NamedPeriod (writer GEOPACKAGE_1)
    attributes: parentFeature_ID text(50), timeInterval_ID mediumint, dayPeriod_ID mediumint, namedPeriod text(50)

Bookmark: Manage attributes
AttributeRenamer_25
    ATTR_TABLE:
      RENAME_SET_DEFAULT timeInterval{0}.TemporalPropertyType.namedDate{0} > date000
      RENAME_SET_DEFAULT timeInterval{1}.TemporalPropertyType.namedDate{0} > date100
      RENAME_SET_DEFAULT timeInterval{2}.TemporalPropertyType.namedDate{0} > date200
      RENAME_SET_DEFAULT timeInterval{0}.TemporalPropertyType.namedDate{1} > date001
      RENAME_SET_DEFAULT timeInterval{1}.TemporalPropertyType.namedDate{1} > date101
      RENAME_SET_DEFAULT timeInterval{2}.TemporalPropertyType.namedDate{1} > date201
      RENAME_SET_DEFAULT timeInterval{0}.TemporalPropertyType.namedDate{2} > date002
      RENAME_SET_DEFAULT timeInterval{1}.TemporalPropertyType.namedDate{2} > date102
      RENAME_SET_DEFAULT timeInterval{2}.TemporalPropertyType.namedDate{2} > date202
      RENAME_SET_DEFAULT timeInterval{0}.TemporalPropertyType.dayPeriod{0}.DayPropertyType.namedDay{0} > day000
      RENAME_SET_DEFAULT timeInterval{1}.TemporalPropertyType.dayPeriod{0}.DayPropertyType.namedDay{0} > day100
      RENAME_SET_DEFAULT timeInterval{2}.TemporalPropertyType.dayPeriod{0}.DayPropertyType.namedDay{0} > day200
      RENAME_SET_DEFAULT timeInterval{0}.TemporalPropertyType.dayPeriod{0}.DayPropertyType.namedDay{1} > day001
      RENAME_SET_DEFAULT timeInterval{1}.TemporalPropertyType.dayPeriod{0}.DayPropertyType.namedDay{1} > day101
      RENAME_SET_DEFAULT timeInterval{2}.TemporalPropertyType.dayPeriod{0}.DayPropertyType.namedDay{1} > day201
      RENAME_SET_DEFAULT timeInterval{0}.TemporalPropertyType.dayPeriod{0}.DayPropertyType.namedDay{2} > day002
      RENAME_SET_DEFAULT timeInterval{1}.TemporalPropertyType.dayPeriod{0}.DayPropertyType.namedDay{2} > day102
      RENAME_SET_DEFAULT timeInterval{2}.TemporalPropertyType.dayPeriod{0}.DayPropertyType.namedDay{2} > day202
      RENAME_SET_DEFAULT timeInterval{0}.TemporalPropertyType.dayPeriod{0}.DayPropertyType.namedDay{3} > day003
      RENAME_SET_DEFAULT timeInterval{1}.TemporalPropertyType.dayPeriod{0}.DayPropertyType.namedDay{3} > day103
      RENAME_SET_DEFAULT timeInterval{2}.TemporalPropertyType.dayPeriod{0}.DayPropertyType.namedDay{3} > day203
      RENAME_SET_DEFAULT timeInterval{0}.TemporalPropertyType.dayPeriod{0}.DayPropertyType.namedDay{4} > day004
      RENAME_SET_DEFAULT timeInterval{1}.TemporalPropertyType.dayPeriod{0}.DayPropertyType.namedDay{4} > day104
      RENAME_SET_DEFAULT timeInterval{2}.TemporalPropertyType.dayPeriod{0}.DayPropertyType.namedDay{4} > day204
      RENAME_SET_DEFAULT timeInterval{0}.TemporalPropertyType.dayPeriod{0}.DayPropertyType.namedDay{5} > day005
      RENAME_SET_DEFAULT timeInterval{1}.TemporalPropertyType.dayPeriod{0}.DayPropertyType.namedDay{5} > day105
      RENAME_SET_DEFAULT timeInterval{2}.TemporalPropertyType.dayPeriod{0}.DayPropertyType.namedDay{5} > day205
      RENAME_SET_DEFAULT timeInterval{0}.TemporalPropertyType.dayPeriod{0}.DayPropertyType.namedDay{6} > day006
      RENAME_SET_DEFAULT timeInterval{1}.TemporalPropertyType.dayPeriod{0}.DayPropertyType.namedDay{6} > day106
      RENAME_SET_DEFAULT timeInterval{2}.TemporalPropertyType.dayPeriod{0}.DayPropertyType.namedDay{6} > day206
      RENAME_SET_DEFAULT timeInterval{0}.TemporalPropertyType.dayPeriod{0}.DayPropertyType.namedPeriod{0} > period000
      RENAME_SET_DEFAULT timeInterval{1}.TemporalPropertyType.dayPeriod{0}.DayPropertyType.namedPeriod{0} > period100
      RENAME_SET_DEFAULT timeInterval{2}.TemporalPropertyType.dayPeriod{0}.DayPropertyType.namedPeriod{0} > period200
      RENAME_SET_DEFAULT timeInterval{0}.TemporalPropertyType.dayPeriod{0}.DayPropertyType.namedPeriod{1} > period001
      RENAME_SET_DEFAULT timeInterval{1}.TemporalPropertyType.dayPeriod{0}.DayPropertyType.namedPeriod{1} > period101
      RENAME_SET_DEFAULT timeInterval{2}.TemporalPropertyType.dayPeriod{0}.DayPropertyType.namedPeriod{1} > period201
      RENAME_SET_DEFAULT timeInterval{0}.TemporalPropertyType.dayPeriod{0}.DayPropertyType.namedPeriod{2} > period002
      RENAME_SET_DEFAULT timeInterval{1}.TemporalPropertyType.dayPeriod{0}.DayPropertyType.namedPeriod{2} > period102
      RENAME_SET_DEFAULT timeInterval{2}.TemporalPropertyType.dayPeriod{0}.DayPropertyType.namedPeriod{2} > period202
      RENAME_SET_DEFAULT timeInterval{0}.TemporalPropertyType.dayPeriod{0}.DayPropertyType.timePeriod{0}.TimePropertyType.namedTime{0} > time000
      RENAME_SET_DEFAULT timeInterval{1}.TemporalPropertyType.dayPeriod{0}.DayPropertyType.timePeriod{0}.TimePropertyType.namedTime{0} > time100
      RENAME_SET_DEFAULT timeInterval{2}.TemporalPropertyType.dayPeriod{0}.DayPropertyType.timePeriod{0}.TimePropertyType.namedTime{0} > time200
      RENAME_SET_DEFAULT timeInterval{0}.TemporalPropertyType.dayPeriod{0}.DayPropertyType.timePeriod{0}.TimePropertyType.namedTime{1} > time001
      RENAME_SET_DEFAULT timeInterval{1}.TemporalPropertyType.dayPeriod{0}.DayPropertyType.timePeriod{0}.TimePropertyType.namedTime{1} > time101
      RENAME_SET_DEFAULT timeInterval{2}.TemporalPropertyType.dayPeriod{0}.DayPropertyType.timePeriod{0}.TimePropertyType.namedTime{1} > time201
      RENAME_SET_DEFAULT timeInterval{0}.TemporalPropertyType.dayPeriod{0}.DayPropertyType.timePeriod{0}.TimePropertyType.namedTime{2} > time002
      RENAME_SET_DEFAULT timeInterval{1}.TemporalPropertyType.dayPeriod{0}.DayPropertyType.timePeriod{0}.TimePropertyType.namedTime{2} > time102
      RENAME_SET_DEFAULT timeInterval{2}.TemporalPropertyType.dayPeriod{0}.DayPropertyType.timePeriod{0}.TimePropertyType.namedTime{2} > time202
      RENAME_SET_DEFAULT timeInterval{0}.TemporalPropertyType.dateRange{0}.DateRangeType.startMonthDay > monthdaystart0
      RENAME_SET_DEFAULT timeInterval{1}.TemporalPropertyType.dateRange{0}.DateRangeType.startMonthDay > monthdaystart1
      RENAME_SET_DEFAULT timeInterval{2}.TemporalPropertyType.dateRange{0}.DateRangeType.startMonthDay > monthdaystart2
      RENAME_SET_DEFAULT timeInterval{0}.TemporalPropertyType.dateRange{0}.DateRangeType.endMonthDay > monthdayend0
      RENAME_SET_DEFAULT timeInterval{1}.TemporalPropertyType.dateRange{0}.DateRangeType.endMonthDay > monthdayend1
      RENAME_SET_DEFAULT timeInterval{2}.TemporalPropertyType.dateRange{0}.DateRangeType.startMonthDay > monthdayend2
      RENAME_SET_DEFAULT timeInterval{0}.TemporalPropertyType.dayPeriod{0}.DayPropertyType.timePeriod{0}.TimePropertyType.timeRange{0}.TimeRangeType.startTime > 1sttimestart0
      RENAME_SET_DEFAULT timeInterval{0}.TemporalPropertyType.dayPeriod{0}.DayPropertyType.timePeriod{1}.TimePropertyType.timeRange{0}.TimeRangeType.startTime > 1sttimestart1
      RENAME_SET_DEFAULT timeInterval{0}.TemporalPropertyType.dayPeriod{0}.DayPropertyType.timePeriod{2}.TimePropertyType.timeRange{0}.TimeRangeType.startTime > 1sttimestart2
      RENAME_SET_DEFAULT timeInterval{0}.TemporalPropertyType.dayPeriod{0}.DayPropertyType.timePeriod{3}.TimePropertyType.timeRange{0}.TimeRangeType.startTime > 1sttimestart3
      RENAME_SET_DEFAULT timeInterval{1}.TemporalPropertyType.dayPeriod{0}.DayPropertyType.timePeriod{0}.TimePropertyType.timeRange{0}.TimeRangeType.startTime > 2ndtimestart0
      RENAME_SET_DEFAULT timeInterval{1}.TemporalPropertyType.dayPeriod{0}.DayPropertyType.timePeriod{1}.TimePropertyType.timeRange{0}.TimeRangeType.startTime > 2ndtimestart1
      RENAME_SET_DEFAULT timeInterval{1}.TemporalPropertyType.dayPeriod{0}.DayPropertyType.timePeriod{2}.TimePropertyType.timeRange{0}.TimeRangeType.startTime > 2ndtimestart2
      RENAME_SET_DEFAULT timeInterval{1}.TemporalPropertyType.dayPeriod{0}.DayPropertyType.timePeriod{3}.TimePropertyType.timeRange{0}.TimeRangeType.startTime > 2ndtimestart3
      RENAME_SET_DEFAULT timeInterval{2}.TemporalPropertyType.dayPeriod{0}.DayPropertyType.timePeriod{0}.TimePropertyType.timeRange{0}.TimeRangeType.startTime > 3rdtimestart0
      RENAME_SET_DEFAULT timeInterval{2}.TemporalPropertyType.dayPeriod{0}.DayPropertyType.timePeriod{1}.TimePropertyType.timeRange{0}.TimeRangeType.startTime > 3rdtimestart1
      RENAME_SET_DEFAULT timeInterval{2}.TemporalPropertyType.dayPeriod{0}.DayPropertyType.timePeriod{2}.TimePropertyType.timeRange{0}.TimeRangeType.startTime > 3rdtimestart2
      RENAME_SET_DEFAULT timeInterval{2}.TemporalPropertyType.dayPeriod{0}.DayPropertyType.timePeriod{3}.TimePropertyType.timeRange{0}.TimeRangeType.startTime > 3rdtimestart3
      RENAME_SET_DEFAULT timeInterval{0}.TemporalPropertyType.dayPeriod{0}.DayPropertyType.timePeriod{0}.TimePropertyType.timeRange{0}.TimeRangeType.endTime > 1sttimeend0
      RENAME_SET_DEFAULT timeInterval{0}.TemporalPropertyType.dayPeriod{0}.DayPropertyType.timePeriod{1}.TimePropertyType.timeRange{0}.TimeRangeType.endTime > 1sttimeend1
      RENAME_SET_DEFAULT timeInterval{0}.TemporalPropertyType.dayPeriod{0}.DayPropertyType.timePeriod{2}.TimePropertyType.timeRange{0}.TimeRangeType.endTime > 1sttimeend2
      RENAME_SET_DEFAULT timeInterval{0}.TemporalPropertyType.dayPeriod{0}.DayPropertyType.timePeriod{3}.TimePropertyType.timeRange{0}.TimeRangeType.endTime > 1sttimeend3
      RENAME_SET_DEFAULT timeInterval{1}.TemporalPropertyType.dayPeriod{0}.DayPropertyType.timePeriod{0}.TimePropertyType.timeRange{0}.TimeRangeType.endTime > 2ndtimeend0
      RENAME_SET_DEFAULT timeInterval{1}.TemporalPropertyType.dayPeriod{0}.DayPropertyType.timePeriod{1}.TimePropertyType.timeRange{0}.TimeRangeType.endTime > 2ndtimeend1
      RENAME_SET_DEFAULT timeInterval{1}.TemporalPropertyType.dayPeriod{0}.DayPropertyType.timePeriod{2}.TimePropertyType.timeRange{0}.TimeRangeType.endTime > 2ndtimeend2
      RENAME_SET_DEFAULT timeInterval{1}.TemporalPropertyType.dayPeriod{0}.DayPropertyType.timePeriod{3}.TimePropertyType.timeRange{0}.TimeRangeType.endTime > 2ndtimeend3
      RENAME_SET_DEFAULT timeInterval{2}.TemporalPropertyType.dayPeriod{0}.DayPropertyType.timePeriod{0}.TimePropertyType.timeRange{0}.TimeRangeType.endTime > 3rdtimeend0
      RENAME_SET_DEFAULT timeInterval{2}.TemporalPropertyType.dayPeriod{0}.DayPropertyType.timePeriod{1}.TimePropertyType.timeRange{0}.TimeRangeType.endTime > 3rdtimeend1
      RENAME_SET_DEFAULT timeInterval{2}.TemporalPropertyType.dayPeriod{0}.DayPropertyType.timePeriod{2}.TimePropertyType.timeRange{0}.TimeRangeType.endTime > 3rdtimeend2
      RENAME_SET_DEFAULT timeInterval{2}.TemporalPropertyType.dayPeriod{0}.DayPropertyType.timePeriod{3}.TimePropertyType.timeRange{0}.TimeRangeType.endTime > 3rdtimeend3
      RENAME_SET_DEFAULT timeInterval{0}.TemporalPropertyType.dateRange{0}.DateRangeType.startDate > 1ststartdate
      RENAME_SET_DEFAULT timeInterval{1}.TemporalPropertyType.dateRange{0}.DateRangeType.startDate > 2ndstartdate
      RENAME_SET_DEFAULT timeInterval{2}.TemporalPropertyType.dateRange{0}.DateRangeType.startDate > 3rdstartdate
      RENAME_SET_DEFAULT timeInterval{0}.TemporalPropertyType.dateRange{0}.DateRangeType.endDate > 1stenddate
      RENAME_SET_DEFAULT timeInterval{1}.TemporalPropertyType.dateRange{0}.DateRangeType.endDate > 2ndenddate
      RENAME_SET_DEFAULT timeInterval{2}.TemporalPropertyType.dateRange{0}.DateRangeType.endDate > 3rdenddate
    -> StringReplacer_4
StringReplacer_4
    CASE = NO
    FIND_TEXT = ([0-9][0-9]:[0-9][0-9]):[0-9][0-9]
    NO_MATCH = _FME_NO_OP_
    REGEXP = YES
    REPLACE_TEXT = \1
    SRC_ATTRS = 2ndtimeend3,3rdtimestart3,2ndtimeend1,1sttimeend2,3rdtimestart2,3rdtimeend3,3rdtimeend2,1sttimeend0,1sttimeend1,3rdtimestart0,2ndtimestart0,3rdtimestart1,2ndtimeend2,2ndtimestart2,1sttimestart0,3rdtimeend0,2ndtimestart3,1sttimestart3,2ndtimeend0,1sttimestart2,1sttimeend3,2ndtimestart1,3rdtimeend1,1sttimestart1
    -> StringReplacer_8
StringReplacer_8
    CASE = NO
    FIND_TEXT = Monday
    NO_MATCH = _FME_NO_OP_
    REGEXP = NO
    REPLACE_TEXT = Mon
    SRC_ATTRS = day204,day101,day002,day004,day105,day201,day203,day100,day104,day202,day206,day103,day003,day102,day000,day200,day205,day106,day001,day005,day006
    -> StringReplacer_9
StringReplacer_9
    CASE = NO
    FIND_TEXT = Tuesday
    NO_MATCH = _FME_NO_OP_
    REGEXP = NO
    REPLACE_TEXT = Tue
    SRC_ATTRS = day204,day101,day002,day004,day105,day201,day203,day100,day104,day202,day206,day103,day003,day102,day000,day200,day205,day106,day001,day005,day006
    -> StringReplacer_13
StringReplacer_13
    CASE = NO
    FIND_TEXT = Wednesday
    NO_MATCH = _FME_NO_OP_
    REGEXP = NO
    REPLACE_TEXT = Wed
    SRC_ATTRS = day006,day000,day105,day101,day203,day003,day103,day200,day001,day204,day201,day104,day002,day106,day205,day206,day102,day202,day004,day005,day100
    -> StringReplacer_23
StringReplacer_23
    CASE = NO
    FIND_TEXT = Thursday
    NO_MATCH = _FME_NO_OP_
    REGEXP = NO
    REPLACE_TEXT = Thu
    SRC_ATTRS = day204,day101,day002,day004,day105,day201,day203,day100,day104,day202,day206,day103,day003,day102,day000,day200,day205,day106,day001,day005,day006
    -> StringReplacer_25
StringReplacer_25
    CASE = NO
    FIND_TEXT = Friday
    NO_MATCH = _FME_NO_OP_
    REGEXP = NO
    REPLACE_TEXT = Fri
    SRC_ATTRS = day204,day101,day002,day004,day105,day201,day203,day100,day104,day202,day206,day103,day003,day102,day000,day200,day205,day106,day001,day005,day006
    -> StringReplacer_32
StringReplacer_32
    CASE = NO
    FIND_TEXT = Saturday
    NO_MATCH = _FME_NO_OP_
    REGEXP = NO
    REPLACE_TEXT = Sat
    SRC_ATTRS = day204,day101,day002,day004,day105,day201,day203,day100,day104,day202,day206,day103,day003,day102,day000,day200,day205,day106,day001,day005,day006
    -> StringReplacer_33
StringReplacer_33
    CASE = NO
    FIND_TEXT = Sunday
    NO_MATCH = _FME_NO_OP_
    REGEXP = NO
    REPLACE_TEXT = Sun
    SRC_ATTRS = day204,day101,day002,day004,day105,day201,day203,day100,day104,day202,day206,day103,day003,day102,day000,day200,day205,day106,day001,day005,day006
    -> SubstringExtractor_5

Bookmark: Format day and month expressions
SubstringExtractor_5
    END = 3
    RESULT_ATTR = 1stmonthstart
    SRC_STRING = @Value(monthdaystart0)
    START = 2
    -> SubstringExtractor_6
SubstringExtractor_6
    END = -1
    RESULT_ATTR = 1stdaystart
    SRC_STRING = @Value(monthdaystart0)
    START = -2
    -> SubstringExtractor_7
SubstringExtractor_7
    END = 3
    RESULT_ATTR = 1stmonthend
    SRC_STRING = @Value(monthdayend0)
    START = 2
    -> SubstringExtractor_8
SubstringExtractor_8
    END = -1
    RESULT_ATTR = 1stdayend
    SRC_STRING = @Value(monthdayend0)
    START = -2
    -> StringPairReplacer_3
StringPairReplacer_3
    CASE = no
    MAP = 01 Jan 02 Feb 03 Mar 04 Apr 05 May 06 Jun 07 Jul 08 Aug 09 Sep 10 Oct 11 Nov 12 Dec
    RESULT_ATTR = 1stmonthstart
    SRC_ATTR = 1stmonthstart
    -> StringPairReplacer_4
StringPairReplacer_4
    CASE = no
    MAP = 01 Jan 02 Feb 03 Mar 04 Apr 05 May 06 Jun 07 Jul 08 Aug 09 Sep 10 Oct 11 Nov 12 Dec
    RESULT_ATTR = 1stmonthend
    SRC_ATTR = 1stmonthend
    -> SubstringExtractor_2
SubstringExtractor_2
    END = 3
    RESULT_ATTR = 2ndmonthstart
    SRC_STRING = @Value(monthdaystart1)
    START = 2
    -> SubstringExtractor_3
SubstringExtractor_3
    END = -1
    RESULT_ATTR = 2nddaystart
    SRC_STRING = @Value(monthdaystart1)
    START = -2
    -> SubstringExtractor_4
SubstringExtractor_4
    END = 3
    RESULT_ATTR = 2ndmonthend
    SRC_STRING = @Value(monthdayend1)
    START = 2
    -> SubstringExtractor_9
SubstringExtractor_9
    END = -1
    RESULT_ATTR = 2nddayend
    SRC_STRING = @Value(monthdayend1)
    START = -2
    -> StringPairReplacer_2
StringPairReplacer_2
    CASE = no
    MAP = 01 Jan 02 Feb 03 Mar 04 Apr 05 May 06 Jun 07 Jul 08 Aug 09 Sep 10 Oct 11 Nov 12 Dec
    RESULT_ATTR = 2ndmonthstart
    SRC_ATTR = 2ndmonthstart
    -> StringPairReplacer_5
StringPairReplacer_5
    CASE = no
    MAP = 01 Jan 02 Feb 03 Mar 04 Apr 05 May 06 Jun 07 Jul 08 Aug 09 Sep 10 Oct 11 Nov 12 Dec
    RESULT_ATTR = 2ndmonthend
    SRC_ATTR = 2ndmonthend
    -> SubstringExtractor_10
SubstringExtractor_10
    END = 3
    RESULT_ATTR = 3rdmonthstart
    SRC_STRING = @Value(monthdaystart2)
    START = 2
    -> SubstringExtractor_11
SubstringExtractor_11
    END = -1
    RESULT_ATTR = 3rddaystart
    SRC_STRING = @Value(monthdaystart2)
    START = -2
    -> SubstringExtractor_12
SubstringExtractor_12
    END = 3
    RESULT_ATTR = 3rdmonthend
    SRC_STRING = @Value(monthdayend2)
    START = 2
    -> SubstringExtractor_13
SubstringExtractor_13
    END = -1
    RESULT_ATTR = 3rddayend
    SRC_STRING = @Value(monthdayend2)
    START = -2
    -> StringPairReplacer_6
StringPairReplacer_6
    CASE = no
    MAP = 01 Jan 02 Feb 03 Mar 04 Apr 05 May 06 Jun 07 Jul 08 Aug 09 Sep 10 Oct 11 Nov 12 Dec
    RESULT_ATTR = 3rdmonthstart
    SRC_ATTR = 3rdmonthstart
    -> StringPairReplacer_7
StringPairReplacer_7
    CASE = no
    MAP = 01 Jan 02 Feb 03 Mar 04 Apr 05 May 06 Jun 07 Jul 08 Aug 09 Sep 10 Oct 11 Nov 12 Dec
    RESULT_ATTR = 3rdmonthend
    SRC_ATTR = 3rdmonthend
    -> AttributeCreator_7

Bookmark: Create applicable period 1
AttributeCreator_7
    ATTR_TABLE = SET_TO 1stapplicableperiod = FME_CONDITIONAL:DEFAULT_VALUE''BOOL_OP;AND;COMPOSITE_TEST;<Unused>;TEST @Value(1ststartdate) ATTRIBUTE_HAS_VALUE _FME_BLANK_STRING_;TEST @Value(1stenddate) ATTRIBUTE_HAS_VALUE _FME_BLANK_STRING_'From @Value(1ststartdate) Until @Value(1stenddate)'BOOL_OP;AND;COMPOSITE_TEST;<Unused>;TEST @Value(1ststartdate) ATTRIBUTE_HAS_VALUE _FME_BLANK_STRING_'From @Value(1ststartdate))'BOOL_OP;AND;COMPOSITE_TEST;<Unused>;TEST @Value(1stenddate) ATTRIBUTE_HAS_VALUE _FME_BLANK_STRING_'Until @Value(1stenddate)'FME_NUM_CONDITIONS4___
    -> AttributeCreator_17
AttributeCreator_17
    ATTR_TABLE = SET_TO 1stapplicableperiod = FME_CONDITIONAL:DEFAULT_VALUE''BOOL_OP;AND;COMPOSITE_TEST;<Unused>;TEST @Value(1stapplicableperiod) ATTRIBUTE_HAS_VALUE _FME_BLANK_STRING_;TEST @Value(date002) ATTRIBUTE_HAS_VALUE _FME_BLANK_STRING_'@Value(1stapplicableperiod) - @Value(date000), @Value(date001), @Value(date002)'BOOL_OP;AND;COMPOSITE_TEST;<Unused>;TEST @Value(1stapplicableperiod) ATTRIBUTE_HAS_VALUE _FME_BLANK_STRING_;TEST @Value(date001) ATTRIBUTE_HAS_VALUE _FME_BLANK_STRING_'@Value(1stapplicableperiod) - @Value(date000), @Value(date001)'BOOL_OP;AND;COMPOSITE_TEST;<Unused>;TEST @Value(1stapplicableperiod) ATTRIBUTE_HAS_VALUE _FME_BLANK_STRING_;TEST @Value(date000) ATTRIBUTE_HAS_VALUE _FME_BLANK_STRING_'@Value(1stapplicableperiod) - @Value(date000)'BOOL_OP;AND;COMPOSITE_TEST;<Unused>;TEST @Value(1stapplicableperiod) ATTRIBUTE_HAS_VALUE _FME_BLANK_STRING_'@Value(1stapplicableperiod)'FME_NUM_CONDITIONS5___
    -> AttributeCreator_40
AttributeCreator_40
    ATTR_TABLE = SET_TO 1stapplicableperiod = FME_CONDITIONAL:DEFAULT_VALUE''BOOL_OP;AND;COMPOSITE_TEST;<Unused>;TEST @Value(1stapplicableperiod) ATTRIBUTE_HAS_VALUE _FME_BLANK_STRING_;TEST @Value(1stmonthstart) ATTRIBUTE_HAS_VALUE _FME_BLANK_STRING_'@Value(1stapplicableperiod) - @Value(2nddaystart) @Value(1stmonthstart) To @Value(1stdayend) @Value(1stmonthend)'BOOL_OP;AND;COMPOSITE_TEST;<Unused>;TEST @Value(1stmonthstart) ATTRIBUTE_HAS_VALUE _FME_BLANK_STRING_'@Value(1stdaystart) @Value(1stmonthstart) To @Value(1stdayend) @Value(1stmonthend)'BOOL_OP;AND;COMPOSITE_TEST;<Unused>;TEST @Value(1stapplicableperiod) ATTRIBUTE_HAS_VALUE _FME_BLANK_STRING_'@Value(1stapplicableperiod)'FME_NUM_CONDITIONS4___
    -> AttributeCreator_20
AttributeCreator_20
    ATTR_TABLE = SET_TO 1stnamedperiods = FME_CONDITIONAL:DEFAULT_VALUE'@Value(period000)'BOOL_OP;OR;COMPOSITE_TEST;<Unused>;TEST @Value(period002) ATTRIBUTE_HAS_VALUE _FME_BLANK_STRING_'@Value(period000), @Value(period001), @Value(period002)'BOOL_OP;OR;COMPOSITE_TEST;<Unused>;TEST @Value(period001) ATTRIBUTE_HAS_VALUE _FME_BLANK_STRING_'@Value(period000), @Value(period001)'FME_NUM_CONDITIONS3___
    -> AttributeCreator_19
AttributeCreator_19
    ATTR_TABLE = SET_TO 1stnameddays = FME_CONDITIONAL:DEFAULT_VALUE'@Value(day000)'BOOL_OP;OR;COMPOSITE_TEST;<Unused>;TEST @Value(day006) ATTRIBUTE_HAS_VALUE _FME_BLANK_STRING_'@Value(day000) @Value(day001) @Value(day002) @Value(day003) @Value(day004) @Value(day005) @Value(day006)'BOOL_OP;OR;COMPOSITE_TEST;<Unused>;TEST @Value(day005) ATTRIBUTE_HAS_VALUE _FME_BLANK_STRING_'@Value(day000) @Value(day001) @Value(day002) @Value(day003) @Value(day004) @Value(day005)'BOOL_OP;OR;COMPOSITE_TEST;<Unused>;TEST @Value(day004) ATTRIBUTE_HAS_VALUE _FME_BLANK_STRING_'@Value(day000) @Value(day001) @Value(day002) @Value(day003) @Value(day004)'BOOL_OP;OR;COMPOSITE_TEST;<Unused>;TEST @Value(day003) ATTRIBUTE_HAS_VALUE _FME_BLANK_STRING_'@Value(day000) @Value(day001) @Value(day002) @Value(day003)'BOOL_OP;OR;COMPOSITE_TEST;<Unused>;TEST @Value(day002) ATTRIBUTE_HAS_VALUE _FME_BLANK_STRING_'@Value(day000) @Value(day001) @Value(day002)'BOOL_OP;OR;COMPOSITE_TEST;<Unused>;TEST @Value(day001) ATTRIBUTE_HAS_VALUE _FME_BLANK_STRING_'@Value(day000) @Value(day001)'FME_NUM_CONDITIONS7___
    -> AttributeCreator_33
AttributeCreator_33
    ATTR_TABLE = SET_TO 1stapplicableperiod = FME_CONDITIONAL:DEFAULT_VALUE''BOOL_OP;AND;COMPOSITE_TEST;<Unused>;TEST @Value(1stapplicableperiod) ATTRIBUTE_HAS_VALUE _FME_BLANK_STRING_;TEST @Value(1stnamedperiods) ATTRIBUTE_HAS_VALUE _FME_BLANK_STRING_;TEST @Value(1stnameddays) ATTRIBUTE_HAS_VALUE _FME_BLANK_STRING_'@Value(1stapplicableperiod) - @Value(1stnameddays), @Value(1stnamedperiods)'BOOL_OP;AND;COMPOSITE_TEST;<Unused>;TEST @Value(1stapplicableperiod) ATTRIBUTE_HAS_VALUE _FME_BLANK_STRING_;TEST @Value(1stnamedperiods) ATTRIBUTE_HAS_VALUE _FME_BLANK_STRING_'@Value(1stapplicableperiod) - @Value(1stnamedperiods)'BOOL_OP;AND;COMPOSITE_TEST;<Unused>;TEST @Value(1stapplicableperiod) ATTRIBUTE_HAS_VALUE _FME_BLANK_STRING_;TEST @Value(1stnameddays) ATTRIBUTE_HAS_VALUE _FME_BLANK_STRING_'@Value(1stapplicableperiod) - @Value(1stnameddays)'BOOL_OP;AND;COMPOSITE_TEST;<Unused>;TEST @Value(1stnamedperiods) ATTRIBUTE_HAS_VALUE _FME_BLANK_STRING_;TEST @Value(1stnameddays) ATTRIBUTE_HAS_VALUE _FME_BLANK_STRING_'@Value(1stnameddays), @Value(1stnamedperiods)'BOOL_OP;AND;COMPOSITE_TEST;<Unused>;TEST @Value(1stnamedperiods) ATTRIBUTE_HAS_VALUE _FME_BLANK_STRING_'@Value(1stnamedperiods)'BOOL_OP;AND;COMPOSITE_TEST;<Unused>;TEST @Value(1stnameddays) ATTRIBUTE_HAS_VALUE _FME_BLANK_STRING_'@Value(1stnameddays)'BOOL_OP;AND;COMPOSITE_TEST;<Unused>;TEST @Value(1stapplicableperiod) ATTRIBUTE_HAS_VALUE _FME_BLANK_STRING_'@Value(1stapplicableperiod)'FME_NUM_CONDITIONS8___
    -> AttributeCreator_27
AttributeCreator_27
    ATTR_TABLE = SET_TO 1stnamedtimes = FME_CONDITIONAL:DEFAULT_VALUE'@Value(time000)'BOOL_OP;OR;COMPOSITE_TEST;<Unused>;TEST @Value(time002) ATTRIBUTE_HAS_VALUE _FME_BLANK_STRING_'@Value(time000), @Value(time001), @Value(time002)'BOOL_OP;OR;COMPOSITE_TEST;<Unused>;TEST @Value(time001) ATTRIBUTE_HAS_VALUE _FME_BLANK_STRING_'@Value(time000), @Value(time001)'FME_NUM_CONDITIONS3___
    -> AttributeCreator_46
AttributeCreator_46
    ATTR_TABLE = SET_TO 1sttimerange = FME_CONDITIONAL:DEFAULT_VALUE''BOOL_OP;AND;COMPOSITE_TEST;<Unused>;TEST 1sttimestart3 NOT_ATTRIBUTE_IS_MISSING _FME_BLANK_STRING_;TEST 1sttimeend3 NOT_ATTRIBUTE_IS_MISSING _FME_BLANK_STRING_'@Value(1sttimestart0)-@Value(1sttimeend0) and @Value(1sttimestart1)-@Value(1sttimeend1) and @Value(1sttimestart2)-@Value(1sttimeend2) and @Value(1sttimestart3)-@Value(1sttimeend3)'BOOL_OP;AND;COMPOSITE_TEST;<Unused>;TEST 1sttimestart2 NOT_ATTRIBUTE_IS_MISSING _FME_BLANK_STRING_;TEST 1sttimeend2 NOT_ATTRIBUTE_IS_MISSING _FME_BLANK_STRING_'@Value(1sttimestart0)-@Value(1sttimeend0) and @Value(1sttimestart1)-@Value(1sttimeend1) and @Value(1sttimestart2)-@Value(1sttimeend2)'BOOL_OP;AND;COMPOSITE_TEST;<Unused>;TEST 1sttimestart1 NOT_ATTRIBUTE_IS_MISSING _FME_BLANK_STRING_;TEST 1sttimeend1 NOT_ATTRIBUTE_IS_MISSING _FME_BLANK_STRING_'@Value(1sttimestart0)-@Value(1sttimeend0) and @Value(1sttimestart1)-@Value(1sttimeend1)'BOOL_OP;AND;COMPOSITE_TEST;<Unused>;TEST 1sttimestart0 NOT_ATTRIBUTE_IS_MISSING _FME_BLANK_STRING_;TEST 1sttimeend0 NOT_ATTRIBUTE_IS_MISSING _FME_BLANK_STRING_'@Value(1sttimestart0)-@Value(1sttimeend0)'FME_NUM_CONDITIONS5___
    -> AttributeCreator_34
AttributeCreator_34
    ATTR_TABLE = SET_TO 1stapplicableperiod = FME_CONDITIONAL:DEFAULT_VALUE''BOOL_OP;AND;COMPOSITE_TEST;<Unused>;TEST @Value(1stapplicableperiod) ATTRIBUTE_HAS_VALUE _FME_BLANK_STRING_;TEST @Value(1stnamedtimes) ATTRIBUTE_HAS_VALUE _FME_BLANK_STRING_;TEST @Value(1sttimerange) ATTRIBUTE_HAS_VALUE _FME_BLANK_STRING_'@Value(1stapplicableperiod) @Value(1stnamedtimes) @Value(1sttimerange)'BOOL_OP;AND;COMPOSITE_TEST;<Unused>;TEST @Value(1stapplicableperiod) ATTRIBUTE_HAS_VALUE _FME_BLANK_STRING_;TEST @Value(1stnamedtimes) ATTRIBUTE_HAS_VALUE _FME_BLANK_STRING_'@Value(1stapplicableperiod) @Value(1stnamedtimes)'BOOL_OP;AND;COMPOSITE_TEST;<Unused>;TEST @Value(1stapplicableperiod) ATTRIBUTE_HAS_VALUE _FME_BLANK_STRING_;TEST @Value(1sttimerange) ATTRIBUTE_HAS_VALUE _FME_BLANK_STRING_'@Value(1stapplicableperiod) @Value(1sttimerange)'BOOL_OP;AND;COMPOSITE_TEST;<Unused>;TEST @Value(1stnamedtimes) ATTRIBUTE_HAS_VALUE _FME_BLANK_STRING_;TEST @Value(1sttimerange) ATTRIBUTE_HAS_VALUE _FME_BLANK_STRING_'@Value(1stnamedtimes) @Value(1sttimerange)'BOOL_OP;AND;COMPOSITE_TEST;<Unused>;TEST @Value(1stnamedtimes) ATTRIBUTE_HAS_VALUE _FME_BLANK_STRING_'@Value(1stnamedtimes)'BOOL_OP;AND;COMPOSITE_TEST;<Unused>;TEST @Value(1sttimerange) ATTRIBUTE_HAS_VALUE _FME_BLANK_STRING_'@Value(1sttimerange)'BOOL_OP;AND;COMPOSITE_TEST;<Unused>;TEST @Value(1stapplicableperiod) ATTRIBUTE_HAS_VALUE _FME_BLANK_STRING_'@Value(1stapplicableperiod)'FME_NUM_CONDITIONS8___
    -> AttributeCreator_11

Bookmark: Create applicable period 2
AttributeCreator_11
    ATTR_TABLE = SET_TO 2ndapplicableperiod = FME_CONDITIONAL:DEFAULT_VALUE''BOOL_OP;AND;COMPOSITE_TEST;<Unused>;TEST @Value(2ndstartdate) ATTRIBUTE_HAS_VALUE _FME_BLANK_STRING_;TEST @Value(2ndenddate) ATTRIBUTE_HAS_VALUE _FME_BLANK_STRING_'From @Value(2ndstartdate) Until @Value(2ndenddate)'BOOL_OP;AND;COMPOSITE_TEST;<Unused>;TEST @Value(2ndstartdate) ATTRIBUTE_HAS_VALUE _FME_BLANK_STRING_'From @Value(2ndstartdate))'BOOL_OP;AND;COMPOSITE_TEST;<Unused>;TEST @Value(2ndenddate) ATTRIBUTE_HAS_VALUE _FME_BLANK_STRING_'Until @Value(2ndenddate)'FME_NUM_CONDITIONS4___
    -> AttributeCreator_10
AttributeCreator_10
    ATTR_TABLE = SET_TO 2ndapplicableperiod = FME_CONDITIONAL:DEFAULT_VALUE''BOOL_OP;AND;COMPOSITE_TEST;<Unused>;TEST @Value(2ndapplicableperiod) ATTRIBUTE_HAS_VALUE _FME_BLANK_STRING_;TEST @Value(date102) ATTRIBUTE_HAS_VALUE _FME_BLANK_STRING_'@Value(2ndapplicableperiod) - @Value(date100), @Value(date101), @Value(date102)'BOOL_OP;AND;COMPOSITE_TEST;<Unused>;TEST @Value(2ndapplicableperiod) ATTRIBUTE_HAS_VALUE _FME_BLANK_STRING_;TEST @Value(date101) ATTRIBUTE_HAS_VALUE _FME_BLANK_STRING_'@Value(2ndapplicableperiod) - @Value(date100), @Value(date101)'BOOL_OP;AND;COMPOSITE_TEST;<Unused>;TEST @Value(2ndapplicableperiod) ATTRIBUTE_HAS_VALUE _FME_BLANK_STRING_;TEST @Value(date100) ATTRIBUTE_HAS_VALUE _FME_BLANK_STRING_'@Value(2ndapplicableperiod) - @Value(date100)'BOOL_OP;AND;COMPOSITE_TEST;<Unused>;TEST @Value(2ndapplicableperiod) ATTRIBUTE_HAS_VALUE _FME_BLANK_STRING_'@Value(2ndapplicableperiod)'FME_NUM_CONDITIONS5___
    -> AttributeCreator_9
AttributeCreator_9
    ATTR_TABLE = SET_TO 2ndapplicableperiod = FME_CONDITIONAL:DEFAULT_VALUE''BOOL_OP;AND;COMPOSITE_TEST;<Unused>;TEST @Value(2ndapplicableperiod) ATTRIBUTE_HAS_VALUE _FME_BLANK_STRING_;TEST @Value(2ndmonthstart) ATTRIBUTE_HAS_VALUE _FME_BLANK_STRING_'@Value(2ndapplicableperiod) - @Value(2nddaystart) @Value(2ndmonthstart) To @Value(2nddayend) @Value(2ndmonthend)'BOOL_OP;AND;COMPOSITE_TEST;<Unused>;TEST @Value(2ndmonthstart) ATTRIBUTE_HAS_VALUE _FME_BLANK_STRING_'@Value(2nddaystart) @Value(2ndmonthstart) To @Value(2nddayend) @Value(2ndmonthend)'BOOL_OP;AND;COMPOSITE_TEST;<Unused>;TEST @Value(2ndapplicableperiod) ATTRIBUTE_HAS_VALUE _FME_BLANK_STRING_'@Value(2ndapplicableperiod)'FME_NUM_CONDITIONS4___
    -> AttributeCreator_25
AttributeCreator_25
    ATTR_TABLE = SET_TO 2ndnamedperiods = FME_CONDITIONAL:DEFAULT_VALUE'@Value(period100)'BOOL_OP;OR;COMPOSITE_TEST;<Unused>;TEST @Value(period102) ATTRIBUTE_HAS_VALUE _FME_BLANK_STRING_'@Value(period100), @Value(period101), @Value(period102)'BOOL_OP;OR;COMPOSITE_TEST;<Unused>;TEST @Value(period101) ATTRIBUTE_HAS_VALUE _FME_BLANK_STRING_'@Value(period100), @Value(period101)'FME_NUM_CONDITIONS3___
    -> AttributeCreator_23
AttributeCreator_23
    ATTR_TABLE = SET_TO 2ndnameddays = FME_CONDITIONAL:DEFAULT_VALUE'@Value(day100)'BOOL_OP;OR;COMPOSITE_TEST;<Unused>;TEST @Value(day106) ATTRIBUTE_HAS_VALUE _FME_BLANK_STRING_'@Value(day100) @Value(day101) @Value(day102) @Value(day103) @Value(day104) @Value(day105) @Value(day106)'BOOL_OP;OR;COMPOSITE_TEST;<Unused>;TEST @Value(day105) ATTRIBUTE_HAS_VALUE _FME_BLANK_STRING_'@Value(day100) @Value(day101) @Value(day102) @Value(day103) @Value(day104) @Value(day105)'BOOL_OP;OR;COMPOSITE_TEST;<Unused>;TEST @Value(day104) ATTRIBUTE_HAS_VALUE _FME_BLANK_STRING_'@Value(day100) @Value(day101) @Value(day102) @Value(day103) @Value(day104)'BOOL_OP;OR;COMPOSITE_TEST;<Unused>;TEST @Value(day103) ATTRIBUTE_HAS_VALUE _FME_BLANK_STRING_'@Value(day100) @Value(day101) @Value(day102) @Value(day103)'BOOL_OP;OR;COMPOSITE_TEST;<Unused>;TEST @Value(day102) ATTRIBUTE_HAS_VALUE _FME_BLANK_STRING_'@Value(day100) @Value(day101) @Value(day102)'BOOL_OP;OR;COMPOSITE_TEST;<Unused>;TEST @Value(day101) ATTRIBUTE_HAS_VALUE _FME_BLANK_STRING_'@Value(day100) @Value(day101)'FME_NUM_CONDITIONS7___
    -> AttributeCreator_24
AttributeCreator_24
    ATTR_TABLE = SET_TO 2ndapplicableperiod = FME_CONDITIONAL:DEFAULT_VALUE''BOOL_OP;AND;COMPOSITE_TEST;<Unused>;TEST @Value(2ndapplicableperiod) ATTRIBUTE_HAS_VALUE _FME_BLANK_STRING_;TEST @Value(2ndnamedperiods) ATTRIBUTE_HAS_VALUE _FME_BLANK_STRING_;TEST @Value(2ndnameddays) ATTRIBUTE_HAS_VALUE _FME_BLANK_STRING_'@Value(2ndapplicableperiod) - @Value(2ndnameddays), @Value(2ndnamedperiods)'BOOL_OP;AND;COMPOSITE_TEST;<Unused>;TEST @Value(2ndapplicableperiod) ATTRIBUTE_HAS_VALUE _FME_BLANK_STRING_;TEST @Value(2ndnamedperiods) ATTRIBUTE_HAS_VALUE _FME_BLANK_STRING_'@Value(2ndapplicableperiod) - @Value(2ndnamedperiods)'BOOL_OP;AND;COMPOSITE_TEST;<Unused>;TEST @Value(2ndapplicableperiod) ATTRIBUTE_HAS_VALUE _FME_BLANK_STRING_;TEST @Value(2ndnameddays) ATTRIBUTE_HAS_VALUE _FME_BLANK_STRING_'@Value(2ndapplicableperiod) - @Value(2ndnameddays)'BOOL_OP;AND;COMPOSITE_TEST;<Unused>;TEST @Value(2ndnamedperiods) ATTRIBUTE_HAS_VALUE _FME_BLANK_STRING_;TEST @Value(2ndnameddays) ATTRIBUTE_HAS_VALUE _FME_BLANK_STRING_'@Value(2ndnameddays), @Value(2ndnamedperiods)'BOOL_OP;AND;COMPOSITE_TEST;<Unused>;TEST @Value(2ndnamedperiods) ATTRIBUTE_HAS_VALUE _FME_BLANK_STRING_'@Value(2ndnamedperiods)'BOOL_OP;AND;COMPOSITE_TEST;<Unused>;TEST @Value(2ndnameddays) ATTRIBUTE_HAS_VALUE _FME_BLANK_STRING_'@Value(2ndnameddays)'BOOL_OP;AND;COMPOSITE_TEST;<Unused>;TEST @Value(2ndapplicableperiod) ATTRIBUTE_HAS_VALUE _FME_BLANK_STRING_'@Value(2ndapplicableperiod)'FME_NUM_CONDITIONS8___
    -> AttributeCreator_28
AttributeCreator_28
    ATTR_TABLE = SET_TO 2ndnamedtimes = FME_CONDITIONAL:DEFAULT_VALUE'@Value(time100)'BOOL_OP;OR;COMPOSITE_TEST;<Unused>;TEST @Value(time102) ATTRIBUTE_HAS_VALUE _FME_BLANK_STRING_'@Value(time100), @Value(time101), @Value(time102)'BOOL_OP;OR;COMPOSITE_TEST;<Unused>;TEST @Value(time101) ATTRIBUTE_HAS_VALUE _FME_BLANK_STRING_'@Value(time100), @Value(time101)'FME_NUM_CONDITIONS3___
    -> AttributeCreator_43
AttributeCreator_43
    ATTR_TABLE = SET_TO 2ndtimerange = FME_CONDITIONAL:DEFAULT_VALUE''BOOL_OP;AND;COMPOSITE_TEST;<Unused>;TEST 2ndtimestart3 NOT_ATTRIBUTE_IS_MISSING _FME_BLANK_STRING_;TEST 2ndtimeend3 NOT_ATTRIBUTE_IS_MISSING _FME_BLANK_STRING_'@Value(2ndtimestart0)-@Value(2ndtimeend0) and @Value(2ndtimestart1)-@Value(2ndtimeend1) and @Value(2ndtimestart2)-@Value(2ndtimeend2) and @Value(2ndtimestart3)-@Value(2ndtimeend3)'BOOL_OP;AND;COMPOSITE_TEST;<Unused>;TEST 2ndtimestart2 NOT_ATTRIBUTE_IS_MISSING _FME_BLANK_STRING_;TEST 2ndtimeend2 NOT_ATTRIBUTE_IS_MISSING _FME_BLANK_STRING_'@Value(2ndtimestart0)-@Value(2ndtimeend0) and @Value(2ndtimestart1)-@Value(2ndtimeend1) and @Value(2ndtimestart2)-@Value(2ndtimeend2)'BOOL_OP;AND;COMPOSITE_TEST;<Unused>;TEST 2ndtimestart1 NOT_ATTRIBUTE_IS_MISSING _FME_BLANK_STRING_;TEST 2ndtimeend1 NOT_ATTRIBUTE_IS_MISSING _FME_BLANK_STRING_'@Value(2ndtimestart0)-@Value(2ndtimeend0) and @Value(2ndtimestart1)-@Value(2ndtimeend1)'BOOL_OP;AND;COMPOSITE_TEST;<Unused>;TEST 2ndtimestart0 NOT_ATTRIBUTE_IS_MISSING _FME_BLANK_STRING_;TEST 2ndtimeend0 NOT_ATTRIBUTE_IS_MISSING _FME_BLANK_STRING_'@Value(2ndtimestart0)-@Value(2ndtimeend0)'FME_NUM_CONDITIONS5___
    -> AttributeCreator_26
AttributeCreator_26
    ATTR_TABLE = SET_TO 2ndapplicableperiod = FME_CONDITIONAL:DEFAULT_VALUE''BOOL_OP;AND;COMPOSITE_TEST;<Unused>;TEST @Value(2ndapplicableperiod) ATTRIBUTE_HAS_VALUE _FME_BLANK_STRING_;TEST @Value(2ndnamedtimes) ATTRIBUTE_HAS_VALUE _FME_BLANK_STRING_;TEST @Value(2ndtimerange) ATTRIBUTE_HAS_VALUE _FME_BLANK_STRING_'@Value(2ndapplicableperiod) @Value(2ndnamedtimes) @Value(2ndtimerange)'BOOL_OP;AND;COMPOSITE_TEST;<Unused>;TEST @Value(2ndapplicableperiod) ATTRIBUTE_HAS_VALUE _FME_BLANK_STRING_;TEST @Value(2ndnamedtimes) ATTRIBUTE_HAS_VALUE _FME_BLANK_STRING_'@Value(2ndapplicableperiod) @Value(2ndnamedtimes)'BOOL_OP;AND;COMPOSITE_TEST;<Unused>;TEST @Value(2ndapplicableperiod) ATTRIBUTE_HAS_VALUE _FME_BLANK_STRING_;TEST @Value(2ndtimerange) ATTRIBUTE_HAS_VALUE _FME_BLANK_STRING_'@Value(2ndapplicableperiod) @Value(2ndtimerange)'BOOL_OP;AND;COMPOSITE_TEST;<Unused>;TEST @Value(2ndnamedtimes) ATTRIBUTE_HAS_VALUE _FME_BLANK_STRING_;TEST @Value(2ndtimerange) ATTRIBUTE_HAS_VALUE _FME_BLANK_STRING_'@Value(2ndnamedtimes) @Value(2ndtimerange)'BOOL_OP;AND;COMPOSITE_TEST;<Unused>;TEST @Value(2ndnamedtimes) ATTRIBUTE_HAS_VALUE _FME_BLANK_STRING_'@Value(2ndnamedtimes)'BOOL_OP;AND;COMPOSITE_TEST;<Unused>;TEST @Value(2ndtimerange) ATTRIBUTE_HAS_VALUE _FME_BLANK_STRING_'@Value(2ndtimerange)'BOOL_OP;AND;COMPOSITE_TEST;<Unused>;TEST @Value(2ndapplicableperiod) ATTRIBUTE_HAS_VALUE _FME_BLANK_STRING_'@Value(2ndapplicableperiod)'FME_NUM_CONDITIONS8___
    -> AttributeCreator_13

Bookmark: Create applicable period 3
AttributeCreator_13
    ATTR_TABLE = SET_TO 3rdapplicableperiod = FME_CONDITIONAL:DEFAULT_VALUE''BOOL_OP;AND;COMPOSITE_TEST;<Unused>;TEST @Value(3rdstartdate) ATTRIBUTE_HAS_VALUE _FME_BLANK_STRING_;TEST @Value(3rdenddate) ATTRIBUTE_HAS_VALUE _FME_BLANK_STRING_'From @Value(3rdstartdate) Until @Value(3rdenddate)'BOOL_OP;AND;COMPOSITE_TEST;<Unused>;TEST @Value(3rdstartdate) ATTRIBUTE_HAS_VALUE _FME_BLANK_STRING_'From @Value(3rdstartdate))'BOOL_OP;AND;COMPOSITE_TEST;<Unused>;TEST @Value(3rdenddate) ATTRIBUTE_HAS_VALUE _FME_BLANK_STRING_'Until @Value(3rdenddate)'FME_NUM_CONDITIONS4___
    -> AttributeCreator_12
AttributeCreator_12
    ATTR_TABLE = SET_TO 3rdapplicableperiod = FME_CONDITIONAL:DEFAULT_VALUE''BOOL_OP;AND;COMPOSITE_TEST;<Unused>;TEST @Value(3rdapplicableperiod) ATTRIBUTE_HAS_VALUE _FME_BLANK_STRING_;TEST @Value(date202) ATTRIBUTE_HAS_VALUE _FME_BLANK_STRING_'@Value(3rdapplicableperiod) - @Value(date200), @Value(date201), @Value(date202)'BOOL_OP;AND;COMPOSITE_TEST;<Unused>;TEST @Value(3rdapplicableperiod) ATTRIBUTE_HAS_VALUE _FME_BLANK_STRING_;TEST @Value(date201) ATTRIBUTE_HAS_VALUE _FME_BLANK_STRING_'@Value(3rdapplicableperiod) - @Value(date200), @Value(date201)'BOOL_OP;AND;COMPOSITE_TEST;<Unused>;TEST @Value(3rdapplicableperiod) ATTRIBUTE_HAS_VALUE _FME_BLANK_STRING_;TEST @Value(date200) ATTRIBUTE_HAS_VALUE _FME_BLANK_STRING_'@Value(3rdapplicableperiod) - @Value(date200)'BOOL_OP;AND;COMPOSITE_TEST;<Unused>;TEST @Value(3rdapplicableperiod) ATTRIBUTE_HAS_VALUE _FME_BLANK_STRING_'@Value(3rdapplicableperiod)'FME_NUM_CONDITIONS5___
    -> AttributeCreator_8
AttributeCreator_8
    ATTR_TABLE = SET_TO 3rdapplicableperiod = FME_CONDITIONAL:DEFAULT_VALUE''BOOL_OP;AND;COMPOSITE_TEST;<Unused>;TEST @Value(3rdapplicableperiod) ATTRIBUTE_HAS_VALUE _FME_BLANK_STRING_;TEST @Value(3rdmonthstart) ATTRIBUTE_HAS_VALUE _FME_BLANK_STRING_'@Value(3rdapplicableperiod) - @Value(3rddaystart) @Value(3rdmonthstart) To @Value(3rddayend) @Value(3rdmonthend)'BOOL_OP;AND;COMPOSITE_TEST;<Unused>;TEST @Value(3rdmonthstart) ATTRIBUTE_HAS_VALUE _FME_BLANK_STRING_'@Value(3rddaystart) @Value(3rdmonthstart) To @Value(3rddayend) @Value(3rdmonthend)'BOOL_OP;AND;COMPOSITE_TEST;<Unused>;TEST @Value(3rdapplicableperiod) ATTRIBUTE_HAS_VALUE _FME_BLANK_STRING_'@Value(3rdapplicableperiod)'FME_NUM_CONDITIONS4___
    -> AttributeCreator_36
AttributeCreator_36
    ATTR_TABLE = SET_TO 3rdnamedperiods = FME_CONDITIONAL:DEFAULT_VALUE'@Value(period200)'BOOL_OP;OR;COMPOSITE_TEST;<Unused>;TEST @Value(period202) ATTRIBUTE_HAS_VALUE _FME_BLANK_STRING_'@Value(period200), @Value(period201), @Value(period202)'BOOL_OP;OR;COMPOSITE_TEST;<Unused>;TEST @Value(period201) ATTRIBUTE_HAS_VALUE _FME_BLANK_STRING_'@Value(period200), @Value(period201)'FME_NUM_CONDITIONS3___
    -> AttributeCreator_31
AttributeCreator_31
    ATTR_TABLE = SET_TO 3rdnameddays = FME_CONDITIONAL:DEFAULT_VALUE'@Value(day200)'BOOL_OP;OR;COMPOSITE_TEST;<Unused>;TEST @Value(day206) ATTRIBUTE_HAS_VALUE _FME_BLANK_STRING_'@Value(day200) @Value(day201) @Value(day202) @Value(day203) @Value(day204) @Value(day205) @Value(day206)'BOOL_OP;OR;COMPOSITE_TEST;<Unused>;TEST @Value(day205) ATTRIBUTE_HAS_VALUE _FME_BLANK_STRING_'@Value(day200) @Value(day201) @Value(day202) @Value(day203) @Value(day204) @Value(day205)'BOOL_OP;OR;COMPOSITE_TEST;<Unused>;TEST @Value(day204) ATTRIBUTE_HAS_VALUE _FME_BLANK_STRING_'@Value(day200) @Value(day201) @Value(day202) @Value(day203) @Value(day204)'BOOL_OP;OR;COMPOSITE_TEST;<Unused>;TEST @Value(day203) ATTRIBUTE_HAS_VALUE _FME_BLANK_STRING_'@Value(day200) @Value(day201) @Value(day202) @Value(day203)'BOOL_OP;OR;COMPOSITE_TEST;<Unused>;TEST @Value(day202) ATTRIBUTE_HAS_VALUE _FME_BLANK_STRING_'@Value(day200) @Value(day201) @Value(day202)'BOOL_OP;OR;COMPOSITE_TEST;<Unused>;TEST @Value(day201) ATTRIBUTE_HAS_VALUE _FME_BLANK_STRING_'@Value(day200) @Value(day201)'FME_NUM_CONDITIONS7___
    -> AttributeCreator_35
AttributeCreator_35
    ATTR_TABLE = SET_TO 3rdapplicableperiod = FME_CONDITIONAL:DEFAULT_VALUE''BOOL_OP;AND;COMPOSITE_TEST;<Unused>;TEST @Value(3rdapplicableperiod) ATTRIBUTE_HAS_VALUE _FME_BLANK_STRING_;TEST @Value(3rdnamedperiods) ATTRIBUTE_HAS_VALUE _FME_BLANK_STRING_;TEST @Value(3rdnameddays) ATTRIBUTE_HAS_VALUE _FME_BLANK_STRING_'@Value(3rdapplicableperiod) - @Value(3rdnameddays), @Value(3rdnamedperiods)'BOOL_OP;AND;COMPOSITE_TEST;<Unused>;TEST @Value(3rdapplicableperiod) ATTRIBUTE_HAS_VALUE _FME_BLANK_STRING_;TEST @Value(3rdnamedperiods) ATTRIBUTE_HAS_VALUE _FME_BLANK_STRING_'@Value(3rdapplicableperiod) - @Value(3rdnamedperiods)'BOOL_OP;AND;COMPOSITE_TEST;<Unused>;TEST @Value(3rdapplicableperiod) ATTRIBUTE_HAS_VALUE _FME_BLANK_STRING_;TEST @Value(3rdnameddays) ATTRIBUTE_HAS_VALUE _FME_BLANK_STRING_'@Value(3rdapplicableperiod) - @Value(3rdnameddays)'BOOL_OP;AND;COMPOSITE_TEST;<Unused>;TEST @Value(3rdnamedperiods) ATTRIBUTE_HAS_VALUE _FME_BLANK_STRING_;TEST @Value(3rdnameddays) ATTRIBUTE_HAS_VALUE _FME_BLANK_STRING_'@Value(3rdnameddays), @Value(3rdnamedperiods)'BOOL_OP;AND;COMPOSITE_TEST;<Unused>;TEST @Value(3rdnamedperiods) ATTRIBUTE_HAS_VALUE _FME_BLANK_STRING_'@Value(3rdnamedperiods)'BOOL_OP;AND;COMPOSITE_TEST;<Unused>;TEST @Value(3rdnameddays) ATTRIBUTE_HAS_VALUE _FME_BLANK_STRING_'@Value(3rdnameddays)'BOOL_OP;AND;COMPOSITE_TEST;<Unused>;TEST @Value(3rdapplicableperiod) ATTRIBUTE_HAS_VALUE _FME_BLANK_STRING_'@Value(3rdapplicableperiod)'FME_NUM_CONDITIONS8___
    -> AttributeCreator_38
AttributeCreator_38
    ATTR_TABLE = SET_TO 3rdnamedtimes = FME_CONDITIONAL:DEFAULT_VALUE'@Value(time200)'BOOL_OP;OR;COMPOSITE_TEST;<Unused>;TEST @Value(time202) ATTRIBUTE_HAS_VALUE _FME_BLANK_STRING_'@Value(time200), @Value(time201), @Value(time202)'BOOL_OP;OR;COMPOSITE_TEST;<Unused>;TEST @Value(time201) ATTRIBUTE_HAS_VALUE _FME_BLANK_STRING_'@Value(time200), @Value(time201)'FME_NUM_CONDITIONS3___
    -> AttributeCreator_44
AttributeCreator_44
    ATTR_TABLE = SET_TO 3rdtimerange = FME_CONDITIONAL:DEFAULT_VALUE''BOOL_OP;AND;COMPOSITE_TEST;<Unused>;TEST 3rdtimestart3 NOT_ATTRIBUTE_IS_MISSING _FME_BLANK_STRING_;TEST 3rdtimeend3 NOT_ATTRIBUTE_IS_MISSING _FME_BLANK_STRING_'@Value(3rdtimestart0)-@Value(3rdtimeend0) and @Value(3rdtimestart1)-@Value(3rdtimeend1) and @Value(3rdtimestart2)-@Value(3rdtimeend2) and @Value(3rdtimestart3)-@Value(3rdtimeend3)'BOOL_OP;AND;COMPOSITE_TEST;<Unused>;TEST 3rdtimestart2 NOT_ATTRIBUTE_IS_MISSING _FME_BLANK_STRING_;TEST 3rdtimeend2 NOT_ATTRIBUTE_IS_MISSING _FME_BLANK_STRING_'@Value(3rdtimestart0)-@Value(3rdtimeend0) and @Value(3rdtimestart1)-@Value(3rdtimeend1) and @Value(3rdtimestart2)-@Value(3rdtimeend2)'BOOL_OP;AND;COMPOSITE_TEST;<Unused>;TEST 3rdtimestart1 NOT_ATTRIBUTE_IS_MISSING _FME_BLANK_STRING_;TEST 3rdtimeend1 NOT_ATTRIBUTE_IS_MISSING _FME_BLANK_STRING_'@Value(3rdtimestart0)-@Value(3rdtimeend0) and @Value(3rdtimestart1)-@Value(3rdtimeend1)'BOOL_OP;AND;COMPOSITE_TEST;<Unused>;TEST 3rdtimestart0 NOT_ATTRIBUTE_IS_MISSING _FME_BLANK_STRING_;TEST 3rdtimeend0 NOT_ATTRIBUTE_IS_MISSING _FME_BLANK_STRING_'@Value(3rdtimestart0)-@Value(3rdtimeend0)'FME_NUM_CONDITIONS5___
    -> AttributeCreator_37
AttributeCreator_37
    ATTR_TABLE = SET_TO 3rdapplicableperiod = FME_CONDITIONAL:DEFAULT_VALUE''BOOL_OP;AND;COMPOSITE_TEST;<Unused>;TEST @Value(3rdapplicableperiod) ATTRIBUTE_HAS_VALUE _FME_BLANK_STRING_;TEST @Value(3rdnamedtimes) ATTRIBUTE_HAS_VALUE _FME_BLANK_STRING_;TEST @Value(3rdtimerange) ATTRIBUTE_HAS_VALUE _FME_BLANK_STRING_'@Value(3rdapplicableperiod) @Value(3rdnamedtimes) @Value(3rdtimerange)'BOOL_OP;AND;COMPOSITE_TEST;<Unused>;TEST @Value(3rdapplicableperiod) ATTRIBUTE_HAS_VALUE _FME_BLANK_STRING_;TEST @Value(3rdnamedtimes) ATTRIBUTE_HAS_VALUE _FME_BLANK_STRING_'@Value(3rdapplicableperiod) @Value(3rdnamedtimes)'BOOL_OP;AND;COMPOSITE_TEST;<Unused>;TEST @Value(3rdapplicableperiod) ATTRIBUTE_HAS_VALUE _FME_BLANK_STRING_;TEST @Value(3rdtimerange) ATTRIBUTE_HAS_VALUE _FME_BLANK_STRING_'@Value(3rdapplicableperiod) @Value(3rdtimerange)'BOOL_OP;AND;COMPOSITE_TEST;<Unused>;TEST @Value(3rdnamedtimes) ATTRIBUTE_HAS_VALUE _FME_BLANK_STRING_;TEST @Value(3rdtimerange) ATTRIBUTE_HAS_VALUE _FME_BLANK_STRING_'@Value(3rdnamedtimes) @Value(3rdtimerange)'BOOL_OP;OR;COMPOSITE_TEST;<Unused>;TEST @Value(3rdnamedtimes) ATTRIBUTE_HAS_VALUE _FME_BLANK_STRING_'@Value(3rdnamedtimes)'BOOL_OP;OR;COMPOSITE_TEST;<Unused>;TEST @Value(3rdtimerange) ATTRIBUTE_HAS_VALUE _FME_BLANK_STRING_'@Value(3rdtimerange)'BOOL_OP;OR;COMPOSITE_TEST;<Unused>;TEST @Value(3rdapplicableperiod) ATTRIBUTE_HAS_VALUE _FME_BLANK_STRING_'@Value(3rdapplicableperiod)'FME_NUM_CONDITIONS8___
    -> AttributeCreator_32

Bookmark: Consolidate applicable period
AttributeCreator_32
    ATTR_TABLE = SET_TO ApplicablePeriod = FME_CONDITIONAL:DEFAULT_VALUE'@Value(1stapplicableperiod)'BOOL_OP;AND;COMPOSITE_TEST;<Unused>;TEST @Value(3rdapplicableperiod) ATTRIBUTE_HAS_VALUE _FME_BLANK_STRING_;TEST @Value(3rdapplicableperiod) != @Value(2ndapplicableperiod);TEST @Value(3rdapplicableperiod) != @Value(1stapplicableperiod)'@Value(1stapplicableperiod) | @Value(2ndapplicableperiod) | @Value(3rdapplicableperiod)'BOOL_OP;AND;COMPOSITE_TEST;<Unused>;TEST @Value(2ndapplicableperiod) ATTRIBUTE_HAS_VALUE _FME_BLANK_STRING_;TEST @Value(2ndapplicableperiod) != @Value(1stapplicableperiod)'@Value(1stapplicableperiod) | @Value(2ndapplicableperiod)'FME_NUM_CONDITIONS3___
    -> AttributeKeeper_5
AttributeKeeper_5
    KEEP_ATTRS = RoadLink_TOID,formOfWay,beginLifespanVersion,chunkname,validFrom,TOID,ChainOfNetworkLinks,ApplicablePeriod,Exemption,Sign,sequence,Inclusion,restriction,NoOfNetworkLinks,applicableDirection,identifier,reasonForChange
    -> StringReplacer_2
StringReplacer_2
    CASE = NO
    FIND_TEXT = " 00:00-00:00"
    NO_MATCH = _FME_NO_OP_
    REGEXP = NO
    SRC_ATTRS = ApplicablePeriod
    -> AttributeCreator_50
AttributeCreator_50
    ATTR_TABLE = SET_TO length = @Length()
    -> TestFilter_6

Bookmark: Create geometry
TestFilter_6
    DEFAULT_VALUE = <UNFILTERED>
    TEST_LIST:
      "BOOL_OP,AND,COMPOSITE_TEST,""""""<Unused>"""""",TEST_CLAUSE,TEST @Value(restriction) = One Way
      TEST @Value(formOfWay) = Single Carriageway",OneWaySglCarr,"BOOL_OP,OR,COMPOSITE_TEST,""""""<Unused>"""""",TEST_CLAUSE,TEST @Value(restriction) = One Way",OneWayOther
    OneWaySglCarr -> Snipper_2
    OneWayOther -> AttributeCreator_18
    <UNFILTERED> -> TestFilter_4
AttributeCreator_18
    ATTR_TABLE:
      SET_TO StartMark = FME_CONDITIONAL:DEFAULT_VALUE'0'BOOL_OP;OR;COMPOSITE_TEST;<Unused>;TEST @Length() > 2.01'@Evaluate((0.5*@Value(length))-1)'FME_NUM_CONDITIONS2___
      SET_TO EndMark = FME_CONDITIONAL:DEFAULT_VALUE'@Evaluate(@Value(length))'BOOL_OP;OR;COMPOSITE_TEST;<Unused>;TEST @Length() > 2.01'@Evaluate((0.5*@Value(length))+1)'FME_NUM_CONDITIONS2___
    -> Snipper_6
Snipper_6
    DEAGGREGATE_INPUT = YES
    ENDLOCATIONATTR = @Value(EndMark)
    MEASUREMENTTYPE = 2D
    SNIPMODE = Distance (Value)
    STARTLOCATIONATTR = @Value(StartMark)
    -> TestFilter_4
Snipper_2
    DEAGGREGATE_INPUT = YES
    ENDLOCATIONATTR = (0.6*@Value(length))+1
    MEASUREMENTTYPE = 2D
    SNIPMODE = Distance (Value)
    STARTLOCATIONATTR = (0.6*@Value(length))-1
    -> TestFilter_4
TestFilter_4
    DEFAULT_VALUE = <UNFILTERED>
    TEST_LIST = "BOOL_OP,AND,COMPOSITE_TEST,""""""<Unused>"""""",TEST_CLAUSE,TEST @Value(applicableDirection) = inOppositeDirection",OppositeDir
    OppositeDir -> Orientor
    <UNFILTERED> -> TestFilter
Orientor
    FLIP_APPEARANCES_CHOICE = Yes
    KIND = REVERSE
    ORIENTED -> TestFilter
TestFilter
    DEFAULT_VALUE = <UNFILTERED>
    TEST_LIST:
      "BOOL_OP,AND,COMPOSITE_TEST,""""""<Unused>"""""",TEST_CLAUSE,TEST @Value(restriction) = One Way",OneWay,"BOOL_OP,OR,COMPOSITE_TEST,""""""<Unused>"""""",TEST_CLAUSE,TEST @Value(NoOfNetworkLinks) = 1",SingleLink,"BOOL_OP,AND,COMPOSITE_TEST,""""""<Unused>"""""",TEST_CLAUSE,TEST @Value(sequence) = 0",FirstInChain,"BOOL_OP,AND,COMPOSITE_TEST,""""""<Unused>"""""",TEST_CLAUSE,TEST @Value(sequence) = @Evaluate(@Value(NoOfNetworkLinks)-1)
      TEST @Value(length) > @Evaluate(5)",LastInChain
    OneWay -> AzimuthCalculator [Line]
    OneWay -> Junction
    SingleLink -> Junction
    SingleLink -> AttributeCreator_51
    FirstInChain -> TestFilter_5
    LastInChain -> AttributeCreator_22
    <UNFILTERED> -> Junction
AzimuthCalculator
    -> AttributeCreator_51
AttributeCreator_22
    ATTR_TABLE = SET_TO firstpart = FME_CONDITIONAL:DEFAULT_VALUE'@Length()'BOOL_OP;AND;COMPOSITE_TEST;<Unused>;TEST @Value(restriction) = No Turn;TEST NoOfNeworkLinks = 2;TEST @Value(formOfWay) != Single Carriageway;TEST @Value(formOfWay) != Dual Carriageway;TEST @Value(length) > 5.01'5'BOOL_OP;AND;COMPOSITE_TEST;<Unused>;TEST @Value(restriction) = No Turn;TEST @Value(NoOfNetworkLinks) = 2;TEST @Value(length) > 7.51'7.5'FME_NUM_CONDITIONS3___
    -> Snipper_5
Snipper_5
    DEAGGREGATE_INPUT = YES
    ENDLOCATIONATTR = @Value(firstpart)
    MEASUREMENTTYPE = 2D
    SNIPMODE = Distance (Value)
    STARTLOCATIONATTR = 0
    -> Junction
    -> AzimuthCalculator_3 [Line]
TestFilter_5
    DEFAULT_VALUE = <UNFILTERED>
    TEST_LIST:
      "BOOL_OP,AND,COMPOSITE_TEST,""""""<Unused>"""""",TEST_CLAUSE,TEST @Value(restriction) = No Turn
      TEST @Value(NoOfNetworkLinks) = 2
      TEST @Value(formOfWay) != Single Carriageway
      TEST @Value(formOfWay) != Dual Carriageway",KeepLeft
    KeepLeft -> AttributeCreator_16
    <UNFILTERED> -> AttributeCreator_49
AttributeCreator_16
    ATTR_TABLE = SET_TO lastpart = FME_CONDITIONAL:DEFAULT_VALUE'@Evaluate(@Value(length)-5)'BOOL_OP;OR;COMPOSITE_TEST;<Unused>;TEST @Value(length) < 5.01'0'FME_NUM_CONDITIONS2___
    -> Snipper_4
AttributeCreator_49
    ATTR_TABLE = SET_TO lastpart = FME_CONDITIONAL:DEFAULT_VALUE'@Evaluate(@Value(length)-10)'BOOL_OP;OR;COMPOSITE_TEST;<Unused>;TEST @Value(length) < 10.01'0'FME_NUM_CONDITIONS2___
    -> Snipper_4
Snipper_4
    DEAGGREGATE_INPUT = YES
    ENDLOCATIONATTR = -1
    MEASUREMENTTYPE = 2D
    SNIPMODE = Distance (Value)
    STARTLOCATIONATTR = @Value(lastpart)
    -> Junction
    -> AzimuthCalculator_2 [Line]

Bookmark: Refine turn sign styles
AzimuthCalculator_3
    -> AttributeRenamer_17
AttributeRenamer_17
    ATTR_TABLE = RENAME_SET_DEFAULT acAngle > acAngle2
    -> FeatureJoiner_2 [RIGHT]
AzimuthCalculator_2
    -> AttributeRenamer_18
AttributeRenamer_18
    ATTR_TABLE = RENAME_SET_DEFAULT acAngle > acAngle1
    -> FeatureJoiner_2 [LEFT]
FeatureJoiner_2
    ATTR_CONFLICT_RES = Use Left
    GEOMETRY_HANDLING = Use Left
    JOIN_KEYS = TOID TOID AUTO
    JOIN_MODE = Inner
    JOINED -> TestFilter_3
    UNJOINED_LEFT -> TestFilter_3
TestFilter_3
    DEFAULT_VALUE = <UNFILTERED>
    TEST_LIST:
      "BOOL_OP,AND,COMPOSITE_TEST,""""""<Unused>"""""",TEST_CLAUSE,TEST @Value(restriction) = No Turn
      TEST @Value(NoOfNetworkLinks) = 2
      TEST @Value(formOfWay) != Single Carriageway
      TEST @Value(formOfWay) != Dual Carriageway",KeepLeft
    KeepLeft -> CoordinateExtractor
    <UNFILTERED> -> AttributeCreator_51
CoordinateExtractor
    IND = -1
    MODE = Specify Coordinate
    X_ATTR = x
    Y_ATTR = y
    Z_ATTR = z
    Z_DEFAULT = 0
    -> VertexCreator
VertexCreator
    MODE_NAME = Replace with Point
    XVAL = @Value(x)
    YVAL = @Value(y)
    ZVAL = @Value(z)
    -> TurnRestrictionPoint (writer GEOPACKAGE_1)
AttributeCreator_51
    ATTR_TABLE:
      SET_TO Angle1 = FME_CONDITIONAL:DEFAULT_VALUE'0'BOOL_OP;OR;COMPOSITE_TEST;<Unused>;TEST acAngle1 ATTRIBUTE_HAS_A_VALUE _FME_BLANK_STRING_'@Value(acAngle1)'FME_NUM_CONDITIONS2___
      SET_TO Angle2 = FME_CONDITIONAL:DEFAULT_VALUE'0'BOOL_OP;OR;COMPOSITE_TEST;<Unused>;TEST acAngle2 ATTRIBUTE_HAS_A_VALUE _FME_BLANK_STRING_'@Value(acAngle2)'FME_NUM_CONDITIONS2___
      SET_TO TurnAngle = FME_CONDITIONAL:DEFAULT_VALUE'@Evaluate(@round(@abs(@Value(Angle2)-@Value(Angle1))))'BOOL_OP;OR;COMPOSITE_TEST;<Unused>;TEST @round(@abs(@Value(Angle2)-@Value(Angle1))) > 180'@Evaluate(@round(360-@abs(@Value(Angle2)-@Value(Angle1))))'FME_NUM_CONDITIONS2___
      SET_TO Rotation = FME_CONDITIONAL:DEFAULT_VALUE'0'BOOL_OP;OR;COMPOSITE_TEST;<Unused>;TEST acAngle ATTRIBUTE_HAS_A_VALUE _FME_BLANK_STRING_'@round(@Evaluate(@Value(acAngle)))'FME_NUM_CONDITIONS2___
      SET_TO Xcoord = @XValue()
      SET_TO Ycoord = @YValue()
    -> DuplicateFilter_2
DuplicateFilter_2
    INPUT_ORDERED_CHOICE = No
    KEYATTR = Ycoord Xcoord
    UNIQUE -> Snipper
    DUPLICATE -> Snipper_3
Snipper
    DEAGGREGATE_INPUT = YES
    ENDLOCATIONATTR = 60
    MEASUREMENTTYPE = 3D
    SNIPMODE = Distance (Percentage)
    STARTLOCATIONATTR = 60
    -> TurnRestrictionPoint (writer GEOPACKAGE_1)
Snipper_3
    DEAGGREGATE_INPUT = YES
    ENDLOCATIONATTR = 40
    MEASUREMENTTYPE = 3D
    SNIPMODE = Distance (Percentage)
    STARTLOCATIONATTR = 40
    -> TurnRestrictionPoint (writer GEOPACKAGE_1)
TurnRestrictionPoint (writer GEOPACKAGE_1)
    attributes: TOID text(20), identifier text(16), restriction text(51),indexed, formOfWay text(32), ApplicablePeriod text(180), Inclusion text(100), Exemption text(100), NoOfNetworkLinks smallint, ChainOfNetworkLinks text(190), Rotation smallint, TurnAngle smallint, beginLifespanVersion text(20), reasonForChange text(32), validFrom text(20), chunkname text(50)
Junction
    -> TurnRestrictionLine (writer GEOPACKAGE_2)
TurnRestrictionLine (writer GEOPACKAGE_2)
    attributes: TOID text(20), identifier text(16), restriction text(51),Indexed, sequence float, formOfWay text(32), RoadLink_TOID text(20), ApplicablePeriod text(180), Inclusion text(100), Exemption text(100), NoOfNetworkLinks smallint, ChainOfNetworkLinks text(190), beginLifespanVersion datetime, reasonForChange text(32), validFrom float, chunkname text(50)

FME custom transformer LoopFilter
Tests whether a line is a loop, i.e. whether start and end coordinates match.
The transformers outputs loops through PASSED port, and non-loops through FAILED port.

LINE (input)
    -> LineFilter
LineFilter: GeometryFilter
    BREAK_AGG = No
    GEOM_PORT_NAMES = Line
    LINE -> CoordinateExtractor
CoordinateExtractor
    IND = 0
    MODE = Specify Coordinate
    X_ATTR = _x1
    Y_ATTR = _y1
    Z_ATTR = _z1
    -> CoordinateExtractor_2
CoordinateExtractor_2
    IND = -1
    MODE = Specify Coordinate
    X_ATTR = _x2
    Y_ATTR = _y2
    Z_ATTR = _z2
    -> ExpressionEvaluator
ExpressionEvaluator
    ACTION = Create New Attribute
    EXPRESSION = (@Value(_x1)-@Value(_x2))||(@Value(_y1)-@Value(_y2))
    VAL_ATTR = _isLoop
    -> Tester
Tester
    BOOL_OP = OR
    TEST_CLAUSE = TEST @Value(_isLoop) = 0
    PASSED -> AttributeRemover
    FAILED -> AttributeRemover_2
AttributeRemover
    REMOVE_ATTRS = _z1,_z2,_y1,_y2,_isLoop,_x1,_x2
    -> PASSED (output)
PASSED (output)
AttributeRemover_2
    REMOVE_ATTRS = _z1,_z2,_y1,_y2,_isLoop,_x1,_x2
    -> FAILED (output)
FAILED (output)

FME custom transformer AzimuthCalculator
Calculates the angle and azimuth of a line or a polyline. The azimuth is the angle between the line and the north vector. Angles are measured from the reference point of east (which represents 0 degrees).
Note: For polylines it returns the angle and azimuth of a line connecting the first and the last vertices of the polyline. For retrieving information about each segment of the polyline use PolylineAnalyzer.
Input Ports 
    Input
Input features must contain valid line geometry. 
    Output Ports
    Output
Features are output with new attributes containing the angle and azimuth of the line or polyline. 
    acAngle: Angles increase counterclockwise from the reference point of east (which represents zero degrees).
    acAzimuth: The azimuth value can range from -180 to 180 with north as 0, south as -180, east as 90, and west as -90. 
    <Rejected>
Any features that are not valid line geometry, or are loops (coincident start and end points), will be passed through this port. Rejected features are output with value INVALID_GEOMETRY_TYPE stored in the fme_rejection_code attribute.
    Parameters 
This transformer has no parameters.

Line (input)
    -> GeometryFilter
Note: Removes all intermediate attributes
ATTRIBUTEREMOVER: AttributeRemover
    REMOVE_ATTRS = acX2,acZ1,acZ2,acY1,acY2,acX1
    -> Output (output)
Output (output)
AttributeCreator
    ATTR_TABLE = SET_TO fme_rejection_code = INVALID_GEOMETRY_TYPE
    -> <Rejected> (output)
<Rejected> (output)

Bookmark: Input Filter
  Sorts out all unsuitable features - non linear, and loops.
Note: Passes only lines to / the next transfomer
GeometryFilter
    BREAK_AGG = No
    GEOM_PORT_NAMES = Line
    LINE -> LoopFilter [LINE]
    <UNFILTERED> -> AttributeCreator
Note: Tests whether a / line is a loop
LoopFilter
    PASSED -> LOGGER
    FAILED -> COORDINATEFETCHER
LOGGER: Logger
    MAXCOORDS = 3
    MAXFEATS = 20
    MESSAGE = Feature is a loop
    LOGGED -> AttributeCreator

Bookmark: Angle Calculations
COORDINATEFETCHER: CoordinateExtractor
    IND = 0
    MODE = Specify Coordinate
    X_ATTR = acX1
    Y_ATTR = acY1
    Z_ATTR = acZ1
    Z_DEFAULT = -9999
    -> COORDINATEFETCHER_2
COORDINATEFETCHER_2: CoordinateExtractor
    IND = -1
    MODE = Specify Coordinate
    X_ATTR = acX2
    Y_ATTR = acY2
    Z_ATTR = acZ2
    Z_DEFAULT = -9999
    -> EXPRESSIONEVALUATOR
EXPRESSIONEVALUATOR: ExpressionEvaluator
    ACTION = Create New Attribute
    EXPRESSION = acos((@Value(acX2)-@Value(acX1))/sqrt(pow((@Value(acY2)-@Value(acY1)),2) + pow((@Value(acX2)-@Value(acX1)),2)))* (180/3.1415926535897932)
    VAL_ATTR = acAngle
    -> EXPRESSIONEVALUATOR_2
EXPRESSIONEVALUATOR_2: ExpressionEvaluator
    ACTION = Create New Attribute
    EXPRESSION = ((@Value(acY2)-@Value(acY1))<0)?(360-@Value(acAngle)):(@Value(acAngle))
    VAL_ATTR = acAngle
    -> TESTER

Bookmark: Azimuth Calculations
  Testers check quadrand, and calculate the Azimuth Accordingly
TESTER: Tester
    BOOL_OP = OR
    TEST_CLAUSE = TEST @Value(acAngle) > 90
    PASSED -> TESTER_2
    FAILED -> EXPRESSIONEVALUATOR_4
TESTER_2: Tester
    BOOL_OP = OR
    TEST_CLAUSE = TEST @Value(acAngle) > 270
    PASSED -> EXPRESSIONEVALUATOR_3
    FAILED -> EXPRESSIONEVALUATOR_4
EXPRESSIONEVALUATOR_3: ExpressionEvaluator
    ACTION = Create New Attribute
    EXPRESSION = 450 - @Value(acAngle)
    VAL_ATTR = acAzimuth
    -> ATTRIBUTEREMOVER
EXPRESSIONEVALUATOR_4: ExpressionEvaluator
    ACTION = Create New Attribute
    EXPRESSION = 90 - @Value(acAngle)
    VAL_ATTR = acAzimuth
    -> ATTRIBUTEREMOVER
