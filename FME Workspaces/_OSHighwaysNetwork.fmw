FME workspace _OSHighwaysNetwork.fmw

Parameters:
- MASTER_FILES =   # Supplied folder called EmptyMasterFiles
- ROADS_INPUT =   # Folder containing Rrami*.gz raw data files
- PATHS_INPUT =   # Folder containing Paths*.gz raw data files
- DEST_FOLDER =   # Destination folder to contain all output files

Bookmark: Initial copying of required files
Note: Just run this FME workspace to complete the entire translation. / This may take some time, but may simply be left running unattended. / When starting, choose your folders using the Translation Parameters. / Ignore any warnings of 'failure' for feature types not in your data set.
Note: Other FME workspaces will be run in turn to complete the translation. / All the workspaces to be run must be in the same folder as this one.
Creator
    COORDSYS = OSGB-GPS-2015
    GEOM = <?xml version="1.0" encoding="US_ASCII" standalone="no" ?><geometry><point><coord x="0" y="0"/></point></geometry>
    GEOMTYPE = Geometry Object
    NUM = 1
    CREATED -> FeatureReader [INITIATOR]
FeatureReader
    ATTRIBUTES = PATH,"path_unix,path_windows,path_rootname,path_filename,path_extension,path_filesize,path_ownername,path_readonly,path_modified_date,path_created_date,path_accessed_date,path_directory_unix,path_directory_windows,path_type,fme_geometry{0},fme_basename,fme_dataset"
    ATTR_ACCUM_MODE = Only Use Result
    COMBINE_GEOM = Use Result
    DATASET = $(MASTER_FILES)
    FEATURETYPES = PATH
    FORMAT = PATH
    OUTPUT_FEATURES_DISPLAY = Schema and Data Features
    PATH_GLOB_PATTERN = *
    PATH_PATH_EXPOSE_FORMAT_ATTRS = fme_basename,char(50) fme_dataset,char(50)
    PATH_RECURSE_DIRECTORIES = NO
    PATH_RETRIEVE_FILE_PROPERTIES = NO
    PATH_TYPE = ANY
    PATH -> AttributeManager
AttributeManager
    ATTR_TABLE:
      REMOVE path_unix
      RENAME_SET_VALUE path_windows > filecopy_source_dataset
      REMOVE path_rootname
      RENAME_SET_VALUE path_filename > filecopy_dest_filename
      REMOVE path_extension
      REMOVE path_filesize
      REMOVE path_ownername
      REMOVE path_readonly
      REMOVE path_modified_date
      REMOVE path_created_date
      REMOVE path_accessed_date
      REMOVE path_directory_unix
      REMOVE path_directory_windows
      REMOVE path_type
      REMOVE fme_geometry{0}
      REMOVE fme_basename
      REMOVE fme_dataset
      REMOVE fme_geometry{}
      SET_TO filecopy_dest_dataset = $(DEST_FOLDER)\
    -> FeatureWriter [filecopy]
FeatureWriter
    DATASET = $(DEST_FOLDER)
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = COPY
    FILECOPY_MIME_TYPE = text/plain
    FILECOPY_OVERWRITE_FILE = YES
    FORMAT = FILECOPY
    TOTAL_FEATURES_WRITTEN_ATTR = _total_features_written
    SUMMARY -> RoadLink

Bookmark: Create GPKG files, using workspaces derived from OS OpenSource files, with added value from miso
RoadLink: WorkspaceRunner
    BLOCKING = Yes
    WORKSPACE_FILE = RoadLink.fmw
    WORKSPACE_PARAMETERS = SourceDataset_GML,$(ROADS_INPUT)\Highways_Rrami_RoadLink_*.gml.gz,DestDataset_GEOPACKAGE,$(DEST_FOLDER)\RoadLink.gpkg
    SUCCEEDED -> PathLink
    FAILED -> PathLink
PathLink: WorkspaceRunner
    BLOCKING = Yes
    WORKSPACE_FILE = PathLink.fmw
    WORKSPACE_PARAMETERS = SourceDataset_GML,$(PATHS_INPUT)\Highways_Paths_PathLink_*.gml.gz,DestDataset_GEOPACKAGE,$(DEST_FOLDER)\PathLink.gpkg
    SUCCEEDED -> ConnectingLink
    FAILED -> ConnectingLink
ConnectingLink: WorkspaceRunner
    BLOCKING = Yes
    WORKSPACE_FILE = ConnectingLink.fmw
    WORKSPACE_PARAMETERS = SourceDataset_GML,$(PATHS_INPUT)\Highways_Paths_ConnectingLink_*.gml.gz,DestDataset_GEOPACKAGE,$(DEST_FOLDER)\ConnectingLink.gpkg
    SUCCEEDED -> FerryLink_Roads
    FAILED -> FerryLink_Roads
FerryLink_Roads: WorkspaceRunner
    BLOCKING = Yes
    WORKSPACE_FILE = FerryLink.fmw
    WORKSPACE_PARAMETERS = SourceDataset_GML,$(ROADS_INPUT)\Highways_Rrami_FerryLink_*.gml.gz,DestDataset_GEOPACKAGE,$(DEST_FOLDER)\FerryLink_Roads.gpkg
    SUCCEEDED -> FerryLink_Paths
    FAILED -> FerryLink_Paths
FerryLink_Paths: WorkspaceRunner
    BLOCKING = Yes
    WORKSPACE_FILE = FerryLink.fmw
    WORKSPACE_PARAMETERS = SourceDataset_GML,$(PATHS_INPUT)\Highways_Paths_FerryLink_*.gml.gz,DestDataset_GEOPACKAGE,$(DEST_FOLDER)\FerryLink_Paths.gpkg
    SUCCEEDED -> RoadNode
    FAILED -> RoadNode
RoadNode: WorkspaceRunner
    BLOCKING = Yes
    WORKSPACE_FILE = RoadNode.fmw
    WORKSPACE_PARAMETERS = SourceDataset_GML,$(ROADS_INPUT)\Highways_Rrami_RoadNode_*.gml.gz,DestDataset_GEOPACKAGE,$(DEST_FOLDER)\RoadNode.gpkg
    SUCCEEDED -> PathNode
    FAILED -> PathNode
PathNode: WorkspaceRunner
    BLOCKING = Yes
    WORKSPACE_FILE = PathNode.fmw
    WORKSPACE_PARAMETERS = SourceDataset_GML,$(PATHS_INPUT)\Highways_Paths_PathNode_*.gml.gz,DestDataset_GEOPACKAGE,$(DEST_FOLDER)\PathNode.gpkg
    SUCCEEDED -> ConnectingNode
    FAILED -> ConnectingNode
ConnectingNode: WorkspaceRunner
    BLOCKING = Yes
    WORKSPACE_FILE = ConnectingNode.fmw
    WORKSPACE_PARAMETERS = SourceDataset_GML,$(PATHS_INPUT)\Highways_Paths_ConnectingNode_*.gml.gz,DestDataset_GEOPACKAGE,$(DEST_FOLDER)\ConnectingNode.gpkg
    SUCCEEDED -> FerryNode_Roads
    FAILED -> FerryNode_Roads
FerryNode_Roads: WorkspaceRunner
    BLOCKING = Yes
    WORKSPACE_FILE = FerryNode.fmw
    WORKSPACE_PARAMETERS = SourceDataset_GML,$(ROADS_INPUT)\Highways_Rrami_FerryNode_*.gml.gz,DestDataset_GEOPACKAGE,$(DEST_FOLDER)\FerryNode_Roads.gpkg
    SUCCEEDED -> FerryNode_Paths
    FAILED -> FerryNode_Paths
FerryNode_Paths: WorkspaceRunner
    BLOCKING = Yes
    WORKSPACE_FILE = FerryNode.fmw
    WORKSPACE_PARAMETERS = SourceDataset_GML,$(PATHS_INPUT)\Highways_Paths_FerryNode_*.gml.gz,DestDataset_GEOPACKAGE,$(DEST_FOLDER)\FerryNode_Paths.gpkg
    SUCCEEDED -> Street_Roads
    FAILED -> Street_Roads
Street_Roads: WorkspaceRunner
    BLOCKING = Yes
    WORKSPACE_FILE = Street.fmw
    WORKSPACE_PARAMETERS = SourceDataset_Street,$(ROADS_INPUT)\Highways_Rrami_Street_*.gml.gz,DestDataset_Street,$(DEST_FOLDER)\Street_Roads.gpkg
    SUCCEEDED -> Street_Paths
    FAILED -> Street_Paths
Street_Paths: WorkspaceRunner
    BLOCKING = Yes
    WORKSPACE_FILE = Street.fmw
    WORKSPACE_PARAMETERS = SourceDataset_Street,$(PATHS_INPUT)\Highways_Paths_Street_*.gml.gz,DestDataset_Street,$(DEST_FOLDER)\Street_Paths.gpkg
    SUCCEEDED -> Dedication_Roads
    FAILED -> Dedication_Roads
Dedication_Roads: WorkspaceRunner
    BLOCKING = Yes
    WORKSPACE_FILE = HighwayDedication.fmw
    WORKSPACE_PARAMETERS = SourceDataset_GML,$(ROADS_INPUT)\Highways_Rrami_Dedication_*.gml.gz,DestDataset_GEOPACKAGE,$(DEST_FOLDER)\Dedication_Roads.gpkg
    SUCCEEDED -> Dedication_Paths
    FAILED -> Dedication_Paths
Dedication_Paths: WorkspaceRunner
    BLOCKING = Yes
    WORKSPACE_FILE = HighwayDedication.fmw
    WORKSPACE_PARAMETERS = SourceDataset_GML,$(PATHS_INPUT)\Highways_Paths_Dedication_*.gml.gz,DestDataset_GEOPACKAGE,$(DEST_FOLDER)\Dedication_Paths.gpkg
    SUCCEEDED -> HazardAndStructure
    FAILED -> HazardAndStructure
HazardAndStructure: WorkspaceRunner
    BLOCKING = Yes
    WORKSPACE_FILE = HazardsAndStructures.fmw
    WORKSPACE_PARAMETERS = SourceDataset_Hazard,$(ROADS_INPUT)\Highways_Rrami_Hazard_*.gml.gz,SourceDataset_Structure,$(ROADS_INPUT)\Highways_Rrami_Structure_*.gml.gz,SourceDataset_RoadLink,$(ROADS_INPUT)\Highways_Rrami_RoadLink_*.gml.gz,DestDataset_HazardAndStructure,$(DEST_FOLDER)\HazardAndStructure.gpkg
    SUCCEEDED -> Road
    FAILED -> Road
Road: WorkspaceRunner
    BLOCKING = Yes
    WORKSPACE_FILE = Road.fmw
    WORKSPACE_PARAMETERS = SourceDataset_Road,$(ROADS_INPUT)\Highways_Rrami_Road_*.gml.gz,DestDataset_GEOPACKAGE,$(DEST_FOLDER)\Road.gpkg
    SUCCEEDED -> Path
    FAILED -> Path
Path: WorkspaceRunner
    BLOCKING = Yes
    WORKSPACE_FILE = Path.fmw
    WORKSPACE_PARAMETERS = SourceDataset_GML,$(PATHS_INPUT)\Highways_Paths_Path_*.gml.gz,DestDataset_GEOPACKAGE,$(DEST_FOLDER)\Path.gpkg
    SUCCEEDED -> FerryTerminal_Roads
    FAILED -> FerryTerminal_Roads
FerryTerminal_Roads: WorkspaceRunner
    BLOCKING = Yes
    WORKSPACE_FILE = FerryTerminal.fmw
    WORKSPACE_PARAMETERS = SourceDataset_GML_3,$(ROADS_INPUT)\Highways_Rrami_FerryTerminal_*.gml.gz,DestDataset_GEOPACKAGE,$(DEST_FOLDER)\FerryTerminal_Roads.gpkg
    SUCCEEDED -> FerryTerminal_Paths
    FAILED -> FerryTerminal_Paths
FerryTerminal_Paths: WorkspaceRunner
    BLOCKING = Yes
    WORKSPACE_FILE = FerryTerminal.fmw
    WORKSPACE_PARAMETERS = SourceDataset_GML_3,$(PATHS_INPUT)\Highways_Paths_FerryTerminal_*.gml.gz,DestDataset_GEOPACKAGE,$(DEST_FOLDER)\FerryTerminal_Paths.gpkg
    SUCCEEDED -> RoadJunction
    FAILED -> RoadJunction
RoadJunction: WorkspaceRunner
    BLOCKING = Yes
    WORKSPACE_FILE = RoadJunction.fmw
    WORKSPACE_PARAMETERS = SourceDataset_RoadJunction,$(ROADS_INPUT)\Highways_Rrami_RoadJunction_*.gml*,DestDataset_RoadJunction,$(DEST_FOLDER)\RoadJunction.gpkg
    SUCCEEDED -> AssetManagement_Roads
    FAILED -> AssetManagement_Roads
AssetManagement_Roads: WorkspaceRunner
    BLOCKING = Yes
    WORKSPACE_FILE = AssetManagement.fmw
    WORKSPACE_PARAMETERS = SourceDataset_Maintenance,$(ROADS_INPUT)\Highways_Rrami_Maintenance_*.gml.gz,SourceDataset_Reinstatement,$(ROADS_INPUT)\Highways_Rrami_Reinstatement_*.gml.gz,SourceDataset_SpecialDesignation,$(ROADS_INPUT)\Highways_Rrami_SpecialDesignation_*.gml.gz,SourceDataset_Street,$(ROADS_INPUT)\Highways_Rrami_Street_*.gml.gz,DestDataset_AssetManagement,$(DEST_FOLDER)\AssetManagement_Roads.gpkg,DestDataset_SpDesignation,$(DEST_FOLDER)\SpDesignation_Roads.gpkg
    SUCCEEDED -> AssetManagement_Paths
    FAILED -> AssetManagement_Paths
AssetManagement_Paths: WorkspaceRunner
    BLOCKING = Yes
    WORKSPACE_FILE = AssetManagement.fmw
    WORKSPACE_PARAMETERS = SourceDataset_Maintenance,$(PATHS_INPUT)\Highways_Paths_Maintenance_*.gml.gz,SourceDataset_Reinstatement,$(PATHS_INPUT)\Highways_Paths_Reinstatement_*.gml.gz,SourceDataset_SpecialDesignation,$(PATHS_INPUT)\Highways_Paths_SpecialDesignation_*.gml.gz,SourceDataset_Street,$(PATHS_INPUT)\Highways_Paths_Street_*.gml.gz,DestDataset_AssetManagement,$(DEST_FOLDER)\AssetManagement_Paths.gpkg,DestDataset_SpDesignation,$(DEST_FOLDER)\SpDesignation_Paths.gpkg
    SUCCEEDED -> AccessRestriction
    FAILED -> AccessRestriction
AccessRestriction: WorkspaceRunner
    BLOCKING = Yes
    WORKSPACE_FILE = AccessRestriction.fmw
    WORKSPACE_PARAMETERS = SourceDataset_RoadLink,$(ROADS_INPUT)\Highways_Rrami_RoadLink_*.gml.gz,SourceDataset_GML_3,$(ROADS_INPUT)\Highways_Rrami_AccessRestriction_*.gml.gz,DestDataset_GEOPACKAGE,$(DEST_FOLDER)\AccessRestriction.gpkg
    SUCCEEDED -> TurnRestriction
    FAILED -> TurnRestriction
TurnRestriction: WorkspaceRunner
    BLOCKING = Yes
    WORKSPACE_FILE = TurnRestrictions.fmw
    WORKSPACE_PARAMETERS = SourceDataset_RoadLink,$(ROADS_INPUT)\Highways_Rrami_RoadLink_*.gml.gz,SourceDataset_TurnRestriction,$(ROADS_INPUT)\Highways_Rrami_TurnRestriction_*.gml.gz,DestDataset_GEOPACKAGE,$(DEST_FOLDER)\TurnRestriction.gpkg
    SUCCEEDED -> RestrictionForVehicles
    FAILED -> RestrictionForVehicles
RestrictionForVehicles: WorkspaceRunner
    BLOCKING = Yes
    WORKSPACE_FILE = RestrictionForVehicles.fmw
    WORKSPACE_PARAMETERS = SourceDataset_RoadLink,$(ROADS_INPUT)\Highways_Rrami_RoadLink_*.gml.gz,SourceDataset_GML,$(ROADS_INPUT)\Highways_Rrami_RestrictionForVehicles_*.gml.gz,DestDataset_GEOPACKAGE,$(DEST_FOLDER)\RestrictionForVehicles.gpkg
