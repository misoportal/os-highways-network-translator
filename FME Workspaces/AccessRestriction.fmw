FME workspace AccessRestriction.fmw

Parameters:
- SourceDataset_RoadLink = $(ROAD_DATA_INPUT_FOLDER)\Highways_Rrami_RoadLink_FULL_*.gml*   # Source RoadLink GML File(s)
- SourceDataset_GML_3 = $(ROAD_DATA_INPUT_FOLDER)\Highways_Rrami_AccessRestriction_FULL_*.gml*   # Source AccessRestriction GML File(s)
- DestDataset_GEOPACKAGE = $(MIDDLE_FOLDER)\AccessRestriction.gpkg   # Folder for Middle AccessRestriction Geopackage File

Readers:
- GML_1: GML from $(SourceDataset_RoadLink)
- GML_2: GML from $(SourceDataset_GML_3)

Writers:
- GEOPACKAGE_1: GEOPACKAGE to $(DestDataset_GEOPACKAGE)

Note: Set input to local GML files
AccessRestriction (reader GML_2)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NodeReference.element.owns xml_boolean, networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer,
      networkRef{}.LinkReference.applicableDirection.xsi_nil xml_boolean, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean, networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean, networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer,
      networkRef{}.PointReference.offset.xsi_nil xml_boolean, networkRef{}.PointReference.atPositionGeometry xml_geometry, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64, networkRef{}.SimpleLinearReference.offset.nilReason xml_buffer, networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer,
      networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, restriction.owns xml_boolean, restriction.nilReason xml_buffer, restriction.gml_remoteSchema xml_buffer, restriction.xlink_href xml_buffer, exemption.VehicleQualifier.use{} xml_char(22),
      exemption.VehicleQualifier.use{}.codeSpace xml_char(57), exemption.VehicleQualifier.vehicle{} xml_char(13), exemption.VehicleQualifier.vehicle{}.codeSpace xml_char(61), inclusion.VehicleQualifier.vehicle{} xml_char(30), inclusion.VehicleQualifier.vehicle{}.codeSpace xml_char(61), reasonForChange xml_char(4), reasonForChange.codeSpace xml_char(47), timeInterval{}.TemporalPropertyType.dayPeriod{}.DayPropertyType.namedDay{} xml_char(9), timeInterval{}.TemporalPropertyType.dayPeriod{}.DayPropertyType.namedDay{}.codeSpace xml_char(53), timeInterval{}.TemporalPropertyType.dayPeriod{}.DayPropertyType.namedPeriod{} xml_char(18), timeInterval{}.TemporalPropertyType.dayPeriod{}.DayPropertyType.namedPeriod{}.codeSpace xml_char(56), timeInterval{}.TemporalPropertyType.dayPeriod{}.DayPropertyType.timePeriod{}.TimePropertyType.timeRange{}.TimeRangeType.endTime xml_char(9), timeInterval{}.TemporalPropertyType.dayPeriod{}.DayPropertyType.timePeriod{}.TimePropertyType.timeRange{}.TimeRangeType.startTime xml_char(9), timeInterval{}.TemporalPropertyType.namedDate{} xml_char(9), timeInterval{}.TemporalPropertyType.namedDate{}.codeSpace xml_char(54), trafficSign xml_char(41)
    -> AttributeExposer
Note: Rename attributes
AttributeRenamer
    ATTR_LIST = inspireId.Identifier.versionId,versionId,,restriction.xlink_href,restriction,,inspireId.Identifier.localId,identifier,,gml_id,TOID,
    -> TestFilter
    -> ListExploder_4
    -> ListExploder_3
    -> ListExploder_5
    -> ListExploder_2
    -> ListExploder_6
    -> ListExploder_7
    -> ListExploder_8

Bookmark: miso
AttributeExposer
    ATTR_LIST = exemption.VehicleQualifier.load{},inclusion.VehicleQualifier.load{},inclusion.VehicleQualifier.use{},TemporalPropertyType.dateRange{},TimePropertyType.namedTime{},networkRef{}.PointReference.element.xlink_href
    -> AttributeRenamer_18
AttributeRenamer_18
    ATTR_TABLE = RENAME_SET_DEFAULT fme_basename > chunkname
    -> AttributeRenamer

Bookmark: vehicleQualifer.use values have been exposed
ListExploder_4
    ATTR_ACCUM_MODE = Merge Incoming List
    ATTR_CONFLICT_RES = Use Original
    INDEX_ATTR = _element_index
    LIST_ATTR = exemption.VehicleQualifier.use{}
    LIST_FOUND -> AttributeCreator_2
AttributeCreator_2
    ATTR_LIST = exemptionType,use
    -> AttributeRenamer_4
AttributeRenamer_4
    ATTR_LIST = exemption.VehicleQualifier.use,exemption,
    -> AccessRestriction_Exemption (writer GEOPACKAGE_1)

Bookmark: miso addition
TestFilter
    DEFAULT_VALUE = <UNFILTERED>
    TEST_LIST = "BOOL_OP,OR,COMPOSITE_TEST,""""""<Unused>"""""",TEST_CLAUSE,TEST validFrom ATTRIBUTE_HAS_A_VALUE """,ValidFrom
    ValidFrom -> DateFormatter_3
    <UNFILTERED> -> DateFormatter
DateFormatter_3
    DATE_ATTR = validFrom
    FMT = FME Date (%Y%m%d)
    INVALID_DATE_VALUE = _FME_NO_OP_
    SRCFMT = Unknown - Automatic Detection
    -> DateFormatter

Bookmark: Create AccessRestriction feature
Note: Format dates to DMY
DateFormatter
    DATE_ATTR = beginLifespanVersion
    FMT = FME Date (%Y%m%d)
    INVALID_DATE_VALUE = _FME_NO_OP_
    SRCFMT = %Y"-"%m"-"%d"T"%T
    -> AttributeSplitter
Note: The attribute value for "restrcition" is held as a / URL therefore to extract the value from the URL / the attribute needs splitting after every "/". This / action will create a list. The values after the last / "/" will contain the attribute value.
AttributeSplitter
    ATTR_NAME = restriction
    DELIMITER = /
    DROP_EMPTY_PARTS = No
    LIST_NAME = _list
    TRIM_OPTION = Both
    -> AttributeRenamer_11
Note: Renaming the last list produced by the / AttributeSplitter which holds the attribute / value for the "restriction" attribute.
Note: This is an example output, writer will need to be added for specific output
AttributeRenamer_11
    ATTR_LIST = _list{5},restriction,
    -> AttributeValueMapper

Bookmark: miso addition
AttributeValueMapper
    DEFAULT_VALUE = Access restriction
    DIRECTION = Forward (Source To Destination)
    LUT = forbiddenLegally,Legally forbidden,physicallyImpossible,No physical access,private,Private,publicAccess,Public access,seasonal,Seasonal
    SRC = restriction
    VAL_ATTR = restriction
    -> ListExploder

Bookmark: Indicates the RoadLink the AccessRestriction references
ListExploder
    ATTR_ACCUM_MODE = Merge Incoming List
    ATTR_CONFLICT_RES = Use Original
    INDEX_ATTR = _element_index
    LIST_ATTR = networkRef{}
    LIST_FOUND -> AttributeRenamer_2
AttributeRenamer_2
    ATTR_LIST = PointReference.element.xlink_href,RoadLink_TOID,
    -> AttributeSplitter_3
Note: The attribute value for "directionality" is held as a / URL therefore to extract the value from the URL / the attribute needs splitting after every "/". This / action will create a list. The values after the last / "/" will contain the attribute value.
AttributeSplitter_3
    ATTR_NAME = PointReference.applicableDirection.xlink_href
    DELIMITER = /
    DROP_EMPTY_PARTS = No
    LIST_NAME = _list
    TRIM_OPTION = Both
    -> AttributeRenamer_10
Note: Renaming the last list produced by the / AttributeSplitter which holds the attribute / value for the "directionality" attribute.
AttributeRenamer_10
    ATTR_LIST = _list{5},applicableDirection,,PointReference.atPosition,atPosition,
    -> StringReplacer
Note: remove # from the / feature references
StringReplacer
    CASE = no
    FIND_TEXT = #
    NO_MATCH = _FME_NO_OP_
    REGEXP = no
    SRC_ATTRS = RoadLink_TOID
    -> AccessRestriction_NetworkRef (writer GEOPACKAGE_1)
    -> AttributeRenamer_25
Note: Table reference to the RoadLink that the restriction applies to.
AccessRestriction_NetworkRef (writer GEOPACKAGE_1)
    attributes: TOID text(20), RoadLink_TOID text(20), applicableDirection text(120), atPosition double

Bookmark: Manage attributes
AttributeRenamer_25
    ATTR_TABLE:
      RENAME_SET_DEFAULT timeInterval{0}.TemporalPropertyType.namedDate{0} > date000
      RENAME_SET_DEFAULT timeInterval{1}.TemporalPropertyType.namedDate{0} > date100
      RENAME_SET_DEFAULT timeInterval{2}.TemporalPropertyType.namedDate{0} > date200
      RENAME_SET_DEFAULT timeInterval{0}.TemporalPropertyType.namedDate{1} > date001
      RENAME_SET_DEFAULT timeInterval{1}.TemporalPropertyType.namedDate{1} > date101
      RENAME_SET_DEFAULT timeInterval{2}.TemporalPropertyType.namedDate{1} > date201
      RENAME_SET_DEFAULT timeInterval{0}.TemporalPropertyType.namedDate{2} > date002
      RENAME_SET_DEFAULT timeInterval{1}.TemporalPropertyType.namedDate{2} > date102
      RENAME_SET_DEFAULT timeInterval{2}.TemporalPropertyType.namedDate{2} > date202
      RENAME_SET_DEFAULT timeInterval{0}.TemporalPropertyType.dayPeriod{0}.DayPropertyType.namedDay{0} > day000
      RENAME_SET_DEFAULT timeInterval{1}.TemporalPropertyType.dayPeriod{0}.DayPropertyType.namedDay{0} > day100
      RENAME_SET_DEFAULT timeInterval{2}.TemporalPropertyType.dayPeriod{0}.DayPropertyType.namedDay{0} > day200
      RENAME_SET_DEFAULT timeInterval{0}.TemporalPropertyType.dayPeriod{0}.DayPropertyType.namedDay{1} > day001
      RENAME_SET_DEFAULT timeInterval{1}.TemporalPropertyType.dayPeriod{0}.DayPropertyType.namedDay{1} > day101
      RENAME_SET_DEFAULT timeInterval{2}.TemporalPropertyType.dayPeriod{0}.DayPropertyType.namedDay{1} > day201
      RENAME_SET_DEFAULT timeInterval{0}.TemporalPropertyType.dayPeriod{0}.DayPropertyType.namedDay{2} > day002
      RENAME_SET_DEFAULT timeInterval{1}.TemporalPropertyType.dayPeriod{0}.DayPropertyType.namedDay{2} > day102
      RENAME_SET_DEFAULT timeInterval{2}.TemporalPropertyType.dayPeriod{0}.DayPropertyType.namedDay{2} > day202
      RENAME_SET_DEFAULT timeInterval{0}.TemporalPropertyType.dayPeriod{0}.DayPropertyType.namedDay{3} > day003
      RENAME_SET_DEFAULT timeInterval{1}.TemporalPropertyType.dayPeriod{0}.DayPropertyType.namedDay{3} > day103
      RENAME_SET_DEFAULT timeInterval{2}.TemporalPropertyType.dayPeriod{0}.DayPropertyType.namedDay{3} > day203
      RENAME_SET_DEFAULT timeInterval{0}.TemporalPropertyType.dayPeriod{0}.DayPropertyType.namedDay{4} > day004
      RENAME_SET_DEFAULT timeInterval{1}.TemporalPropertyType.dayPeriod{0}.DayPropertyType.namedDay{4} > day104
      RENAME_SET_DEFAULT timeInterval{2}.TemporalPropertyType.dayPeriod{0}.DayPropertyType.namedDay{4} > day204
      RENAME_SET_DEFAULT timeInterval{0}.TemporalPropertyType.dayPeriod{0}.DayPropertyType.namedDay{5} > day005
      RENAME_SET_DEFAULT timeInterval{1}.TemporalPropertyType.dayPeriod{0}.DayPropertyType.namedDay{5} > day105
      RENAME_SET_DEFAULT timeInterval{2}.TemporalPropertyType.dayPeriod{0}.DayPropertyType.namedDay{5} > day205
      RENAME_SET_DEFAULT timeInterval{0}.TemporalPropertyType.dayPeriod{0}.DayPropertyType.namedDay{6} > day006
      RENAME_SET_DEFAULT timeInterval{1}.TemporalPropertyType.dayPeriod{0}.DayPropertyType.namedDay{6} > day106
      RENAME_SET_DEFAULT timeInterval{2}.TemporalPropertyType.dayPeriod{0}.DayPropertyType.namedDay{6} > day206
      RENAME_SET_DEFAULT timeInterval{0}.TemporalPropertyType.dayPeriod{0}.DayPropertyType.namedPeriod{0} > period000
      RENAME_SET_DEFAULT timeInterval{1}.TemporalPropertyType.dayPeriod{0}.DayPropertyType.namedPeriod{0} > period100
      RENAME_SET_DEFAULT timeInterval{2}.TemporalPropertyType.dayPeriod{0}.DayPropertyType.namedPeriod{0} > period200
      RENAME_SET_DEFAULT timeInterval{0}.TemporalPropertyType.dayPeriod{0}.DayPropertyType.namedPeriod{1} > period001
      RENAME_SET_DEFAULT timeInterval{1}.TemporalPropertyType.dayPeriod{0}.DayPropertyType.namedPeriod{1} > period101
      RENAME_SET_DEFAULT timeInterval{2}.TemporalPropertyType.dayPeriod{0}.DayPropertyType.namedPeriod{1} > period201
      RENAME_SET_DEFAULT timeInterval{0}.TemporalPropertyType.dayPeriod{0}.DayPropertyType.namedPeriod{2} > period002
      RENAME_SET_DEFAULT timeInterval{1}.TemporalPropertyType.dayPeriod{0}.DayPropertyType.namedPeriod{2} > period102
      RENAME_SET_DEFAULT timeInterval{2}.TemporalPropertyType.dayPeriod{0}.DayPropertyType.namedPeriod{2} > period202
      RENAME_SET_DEFAULT timeInterval{0}.TemporalPropertyType.dayPeriod{0}.DayPropertyType.timePeriod{0}.TimePropertyType.namedTime{0} > time000
      RENAME_SET_DEFAULT timeInterval{1}.TemporalPropertyType.dayPeriod{0}.DayPropertyType.timePeriod{0}.TimePropertyType.namedTime{0} > time100
      RENAME_SET_DEFAULT timeInterval{2}.TemporalPropertyType.dayPeriod{0}.DayPropertyType.timePeriod{0}.TimePropertyType.namedTime{0} > time200
      RENAME_SET_DEFAULT timeInterval{0}.TemporalPropertyType.dayPeriod{0}.DayPropertyType.timePeriod{0}.TimePropertyType.namedTime{1} > time001
      RENAME_SET_DEFAULT timeInterval{1}.TemporalPropertyType.dayPeriod{0}.DayPropertyType.timePeriod{0}.TimePropertyType.namedTime{1} > time101
      RENAME_SET_DEFAULT timeInterval{2}.TemporalPropertyType.dayPeriod{0}.DayPropertyType.timePeriod{0}.TimePropertyType.namedTime{1} > time201
      RENAME_SET_DEFAULT timeInterval{0}.TemporalPropertyType.dayPeriod{0}.DayPropertyType.timePeriod{0}.TimePropertyType.namedTime{2} > time002
      RENAME_SET_DEFAULT timeInterval{1}.TemporalPropertyType.dayPeriod{0}.DayPropertyType.timePeriod{0}.TimePropertyType.namedTime{2} > time102
      RENAME_SET_DEFAULT timeInterval{2}.TemporalPropertyType.dayPeriod{0}.DayPropertyType.timePeriod{0}.TimePropertyType.namedTime{2} > time202
      RENAME_SET_DEFAULT timeInterval{0}.TemporalPropertyType.dateRange{0}.DateRangeType.startMonthDay > monthdaystart0
      RENAME_SET_DEFAULT timeInterval{1}.TemporalPropertyType.dateRange{0}.DateRangeType.startMonthDay > monthdaystart1
      RENAME_SET_DEFAULT timeInterval{2}.TemporalPropertyType.dateRange{0}.DateRangeType.startMonthDay > monthdaystart2
      RENAME_SET_DEFAULT timeInterval{0}.TemporalPropertyType.dateRange{0}.DateRangeType.endMonthDay > monthdayend0
      RENAME_SET_DEFAULT timeInterval{1}.TemporalPropertyType.dateRange{0}.DateRangeType.endMonthDay > monthdayend1
      RENAME_SET_DEFAULT timeInterval{2}.TemporalPropertyType.dateRange{0}.DateRangeType.startMonthDay > monthdayend2
      RENAME_SET_DEFAULT timeInterval{0}.TemporalPropertyType.dayPeriod{0}.DayPropertyType.timePeriod{0}.TimePropertyType.timeRange{0}.TimeRangeType.startTime > 1sttimestart0
      RENAME_SET_DEFAULT timeInterval{0}.TemporalPropertyType.dayPeriod{0}.DayPropertyType.timePeriod{1}.TimePropertyType.timeRange{0}.TimeRangeType.startTime > 1sttimestart1
      RENAME_SET_DEFAULT timeInterval{0}.TemporalPropertyType.dayPeriod{0}.DayPropertyType.timePeriod{2}.TimePropertyType.timeRange{0}.TimeRangeType.startTime > 1sttimestart2
      RENAME_SET_DEFAULT timeInterval{0}.TemporalPropertyType.dayPeriod{0}.DayPropertyType.timePeriod{3}.TimePropertyType.timeRange{0}.TimeRangeType.startTime > 1sttimestart3
      RENAME_SET_DEFAULT timeInterval{1}.TemporalPropertyType.dayPeriod{0}.DayPropertyType.timePeriod{0}.TimePropertyType.timeRange{0}.TimeRangeType.startTime > 2ndtimestart0
      RENAME_SET_DEFAULT timeInterval{1}.TemporalPropertyType.dayPeriod{0}.DayPropertyType.timePeriod{1}.TimePropertyType.timeRange{0}.TimeRangeType.startTime > 2ndtimestart1
      RENAME_SET_DEFAULT timeInterval{1}.TemporalPropertyType.dayPeriod{0}.DayPropertyType.timePeriod{2}.TimePropertyType.timeRange{0}.TimeRangeType.startTime > 2ndtimestart2
      RENAME_SET_DEFAULT timeInterval{1}.TemporalPropertyType.dayPeriod{0}.DayPropertyType.timePeriod{3}.TimePropertyType.timeRange{0}.TimeRangeType.startTime > 2ndtimestart3
      RENAME_SET_DEFAULT timeInterval{2}.TemporalPropertyType.dayPeriod{0}.DayPropertyType.timePeriod{0}.TimePropertyType.timeRange{0}.TimeRangeType.startTime > 3rdtimestart0
      RENAME_SET_DEFAULT timeInterval{2}.TemporalPropertyType.dayPeriod{0}.DayPropertyType.timePeriod{1}.TimePropertyType.timeRange{0}.TimeRangeType.startTime > 3rdtimestart1
      RENAME_SET_DEFAULT timeInterval{2}.TemporalPropertyType.dayPeriod{0}.DayPropertyType.timePeriod{2}.TimePropertyType.timeRange{0}.TimeRangeType.startTime > 3rdtimestart2
      RENAME_SET_DEFAULT timeInterval{2}.TemporalPropertyType.dayPeriod{0}.DayPropertyType.timePeriod{3}.TimePropertyType.timeRange{0}.TimeRangeType.startTime > 3rdtimestart3
      RENAME_SET_DEFAULT timeInterval{0}.TemporalPropertyType.dayPeriod{0}.DayPropertyType.timePeriod{0}.TimePropertyType.timeRange{0}.TimeRangeType.endTime > 1sttimeend0
      RENAME_SET_DEFAULT timeInterval{0}.TemporalPropertyType.dayPeriod{0}.DayPropertyType.timePeriod{1}.TimePropertyType.timeRange{0}.TimeRangeType.endTime > 1sttimeend1
      RENAME_SET_DEFAULT timeInterval{0}.TemporalPropertyType.dayPeriod{0}.DayPropertyType.timePeriod{2}.TimePropertyType.timeRange{0}.TimeRangeType.endTime > 1sttimeend2
      RENAME_SET_DEFAULT timeInterval{0}.TemporalPropertyType.dayPeriod{0}.DayPropertyType.timePeriod{3}.TimePropertyType.timeRange{0}.TimeRangeType.endTime > 1sttimeend3
      RENAME_SET_DEFAULT timeInterval{1}.TemporalPropertyType.dayPeriod{0}.DayPropertyType.timePeriod{0}.TimePropertyType.timeRange{0}.TimeRangeType.endTime > 2ndtimeend0
      RENAME_SET_DEFAULT timeInterval{1}.TemporalPropertyType.dayPeriod{0}.DayPropertyType.timePeriod{1}.TimePropertyType.timeRange{0}.TimeRangeType.endTime > 2ndtimeend1
      RENAME_SET_DEFAULT timeInterval{1}.TemporalPropertyType.dayPeriod{0}.DayPropertyType.timePeriod{2}.TimePropertyType.timeRange{0}.TimeRangeType.endTime > 2ndtimeend2
      RENAME_SET_DEFAULT timeInterval{1}.TemporalPropertyType.dayPeriod{0}.DayPropertyType.timePeriod{3}.TimePropertyType.timeRange{0}.TimeRangeType.endTime > 2ndtimeend3
      RENAME_SET_DEFAULT timeInterval{2}.TemporalPropertyType.dayPeriod{0}.DayPropertyType.timePeriod{0}.TimePropertyType.timeRange{0}.TimeRangeType.endTime > 3rdtimeend0
      RENAME_SET_DEFAULT timeInterval{2}.TemporalPropertyType.dayPeriod{0}.DayPropertyType.timePeriod{1}.TimePropertyType.timeRange{0}.TimeRangeType.endTime > 3rdtimeend1
      RENAME_SET_DEFAULT timeInterval{2}.TemporalPropertyType.dayPeriod{0}.DayPropertyType.timePeriod{2}.TimePropertyType.timeRange{0}.TimeRangeType.endTime > 3rdtimeend2
      RENAME_SET_DEFAULT timeInterval{2}.TemporalPropertyType.dayPeriod{0}.DayPropertyType.timePeriod{3}.TimePropertyType.timeRange{0}.TimeRangeType.endTime > 3rdtimeend3
    -> StringReplacer_4
StringReplacer_4
    CASE = NO
    FIND_TEXT = ([0-9][0-9]:[0-9][0-9]):[0-9][0-9]
    NO_MATCH = _FME_NO_OP_
    REGEXP = YES
    REPLACE_TEXT = \1
    SRC_ATTRS = 2ndtimeend3,3rdtimestart3,2ndtimeend1,1sttimeend2,3rdtimestart2,3rdtimeend3,3rdtimeend2,1sttimeend0,1sttimeend1,3rdtimestart0,2ndtimestart0,3rdtimestart1,2ndtimeend2,2ndtimestart2,1sttimestart0,3rdtimeend0,2ndtimestart3,1sttimestart3,2ndtimeend0,1sttimestart2,1sttimeend3,2ndtimestart1,3rdtimeend1,1sttimestart1
    -> StringReplacer_8
StringReplacer_8
    CASE = NO
    FIND_TEXT = Monday
    NO_MATCH = _FME_NO_OP_
    REGEXP = NO
    REPLACE_TEXT = Mon
    SRC_ATTRS = day204,day101,day002,day004,day105,day201,day203,day100,day104,day202,day206,day103,day003,day102,day000,day200,day205,day106,day001,day005,day006
    -> StringReplacer_9
StringReplacer_9
    CASE = NO
    FIND_TEXT = Tuesday
    NO_MATCH = _FME_NO_OP_
    REGEXP = NO
    REPLACE_TEXT = Tue
    SRC_ATTRS = day204,day101,day002,day004,day105,day201,day203,day100,day104,day202,day206,day103,day003,day102,day000,day200,day205,day106,day001,day005,day006
    -> StringReplacer_13
StringReplacer_13
    CASE = NO
    FIND_TEXT = Wednesday
    NO_MATCH = _FME_NO_OP_
    REGEXP = NO
    REPLACE_TEXT = Wed
    SRC_ATTRS = day006,day000,day105,day101,day203,day003,day103,day200,day001,day204,day201,day104,day002,day106,day205,day206,day102,day202,day004,day005,day100
    -> StringReplacer_23
StringReplacer_23
    CASE = NO
    FIND_TEXT = Thursday
    NO_MATCH = _FME_NO_OP_
    REGEXP = NO
    REPLACE_TEXT = Thu
    SRC_ATTRS = day204,day101,day002,day004,day105,day201,day203,day100,day104,day202,day206,day103,day003,day102,day000,day200,day205,day106,day001,day005,day006
    -> StringReplacer_25
StringReplacer_25
    CASE = NO
    FIND_TEXT = Friday
    NO_MATCH = _FME_NO_OP_
    REGEXP = NO
    REPLACE_TEXT = Fri
    SRC_ATTRS = day204,day101,day002,day004,day105,day201,day203,day100,day104,day202,day206,day103,day003,day102,day000,day200,day205,day106,day001,day005,day006
    -> StringReplacer_32
StringReplacer_32
    CASE = NO
    FIND_TEXT = Saturday
    NO_MATCH = _FME_NO_OP_
    REGEXP = NO
    REPLACE_TEXT = Sat
    SRC_ATTRS = day204,day101,day002,day004,day105,day201,day203,day100,day104,day202,day206,day103,day003,day102,day000,day200,day205,day106,day001,day005,day006
    -> StringReplacer_33
StringReplacer_33
    CASE = NO
    FIND_TEXT = Sunday
    NO_MATCH = _FME_NO_OP_
    REGEXP = NO
    REPLACE_TEXT = Sun
    SRC_ATTRS = day204,day101,day002,day004,day105,day201,day203,day100,day104,day202,day206,day103,day003,day102,day000,day200,day205,day106,day001,day005,day006
    -> AttributeSplitter_2
AttributeSplitter_2
    ATTR_NAME = PointReference.applicableDirection.xlink_href
    DELIMITER = /
    DROP_EMPTY_PARTS = No
    LIST_NAME = _list
    TRIM_OPTION = Both
    -> AttributeRenamer_20
AttributeRenamer_20
    ATTR_LIST = _list{5},applicableDirection,,PointReference.atPosition,atPosition,,PointReference.atPositionGeometry,atPositionGeometry,
    -> SubstringExtractor_5

Bookmark: Format day and month expressions
SubstringExtractor_5
    END = 3
    RESULT_ATTR = 1stmonthstart
    SRC_STRING = @Value(monthdaystart0)
    START = 2
    -> SubstringExtractor_6
SubstringExtractor_6
    END = -1
    RESULT_ATTR = 1stdaystart
    SRC_STRING = @Value(monthdaystart0)
    START = -2
    -> SubstringExtractor_7
SubstringExtractor_7
    END = 3
    RESULT_ATTR = 1stmonthend
    SRC_STRING = @Value(monthdayend0)
    START = 2
    -> SubstringExtractor_8
SubstringExtractor_8
    END = -1
    RESULT_ATTR = 1stdayend
    SRC_STRING = @Value(monthdayend0)
    START = -2
    -> StringPairReplacer_3
StringPairReplacer_3
    CASE = no
    MAP = 01 Jan 02 Feb 03 Mar 04 Apr 05 May 06 Jun 07 Jul 08 Aug 09 Sep 10 Oct 11 Nov 12 Dec
    RESULT_ATTR = 1stmonthstart
    SRC_ATTR = 1stmonthstart
    -> StringPairReplacer_4
StringPairReplacer_4
    CASE = no
    MAP = 01 Jan 02 Feb 03 Mar 04 Apr 05 May 06 Jun 07 Jul 08 Aug 09 Sep 10 Oct 11 Nov 12 Dec
    RESULT_ATTR = 1stmonthend
    SRC_ATTR = 1stmonthend
    -> SubstringExtractor_2
SubstringExtractor_2
    END = 3
    RESULT_ATTR = 2ndmonthstart
    SRC_STRING = @Value(monthdaystart1)
    START = 2
    -> SubstringExtractor_3
SubstringExtractor_3
    END = -1
    RESULT_ATTR = 2nddaystart
    SRC_STRING = @Value(monthdaystart1)
    START = -2
    -> SubstringExtractor_4
SubstringExtractor_4
    END = 3
    RESULT_ATTR = 2ndmonthend
    SRC_STRING = @Value(monthdayend1)
    START = 2
    -> SubstringExtractor_9
SubstringExtractor_9
    END = -1
    RESULT_ATTR = 2nddayend
    SRC_STRING = @Value(monthdayend1)
    START = -2
    -> StringPairReplacer_2
StringPairReplacer_2
    CASE = no
    MAP = 01 Jan 02 Feb 03 Mar 04 Apr 05 May 06 Jun 07 Jul 08 Aug 09 Sep 10 Oct 11 Nov 12 Dec
    RESULT_ATTR = 2ndmonthstart
    SRC_ATTR = 2ndmonthstart
    -> StringPairReplacer_5
StringPairReplacer_5
    CASE = no
    MAP = 01 Jan 02 Feb 03 Mar 04 Apr 05 May 06 Jun 07 Jul 08 Aug 09 Sep 10 Oct 11 Nov 12 Dec
    RESULT_ATTR = 2ndmonthend
    SRC_ATTR = 2ndmonthend
    -> SubstringExtractor_10
SubstringExtractor_10
    END = 3
    RESULT_ATTR = 3rdmonthstart
    SRC_STRING = @Value(monthdaystart2)
    START = 2
    -> SubstringExtractor_11
SubstringExtractor_11
    END = -1
    RESULT_ATTR = 3rddaystart
    SRC_STRING = @Value(monthdaystart2)
    START = -2
    -> SubstringExtractor_12
SubstringExtractor_12
    END = 3
    RESULT_ATTR = 3rdmonthend
    SRC_STRING = @Value(monthdayend2)
    START = 2
    -> SubstringExtractor_13
SubstringExtractor_13
    END = -1
    RESULT_ATTR = 3rddayend
    SRC_STRING = @Value(monthdayend2)
    START = -2
    -> StringPairReplacer_6
StringPairReplacer_6
    CASE = no
    MAP = 01 Jan 02 Feb 03 Mar 04 Apr 05 May 06 Jun 07 Jul 08 Aug 09 Sep 10 Oct 11 Nov 12 Dec
    RESULT_ATTR = 3rdmonthstart
    SRC_ATTR = 3rdmonthstart
    -> StringPairReplacer_7
StringPairReplacer_7
    CASE = no
    MAP = 01 Jan 02 Feb 03 Mar 04 Apr 05 May 06 Jun 07 Jul 08 Aug 09 Sep 10 Oct 11 Nov 12 Dec
    RESULT_ATTR = 3rdmonthend
    SRC_ATTR = 3rdmonthend
    -> AttributeCreator_17

Bookmark: Create applicable period 1
AttributeCreator_17
    ATTR_TABLE = SET_TO 1stapplicableperiod = FME_CONDITIONAL:DEFAULT_VALUE'@Value(date000)'BOOL_OP;OR;COMPOSITE_TEST;<Unused>;TEST @Value(date002) ATTRIBUTE_HAS_VALUE _FME_BLANK_STRING_'@Value(date000), @Value(date001), @Value(date002)'BOOL_OP;OR;COMPOSITE_TEST;<Unused>;TEST @Value(date001) ATTRIBUTE_HAS_VALUE _FME_BLANK_STRING_'@Value(date000), @Value(date001)'FME_NUM_CONDITIONS3___
    -> AttributeCreator_40
AttributeCreator_40
    ATTR_TABLE = SET_TO 1stapplicableperiod = FME_CONDITIONAL:DEFAULT_VALUE''BOOL_OP;AND;COMPOSITE_TEST;<Unused>;TEST @Value(1stapplicableperiod) ATTRIBUTE_HAS_VALUE _FME_BLANK_STRING_;TEST @Value(1stmonthstart) ATTRIBUTE_HAS_VALUE _FME_BLANK_STRING_'@Value(1stapplicableperiod) - @Value(2nddaystart) @Value(1stmonthstart) To @Value(1stdayend) @Value(1stmonthend)'BOOL_OP;AND;COMPOSITE_TEST;<Unused>;TEST @Value(1stmonthstart) ATTRIBUTE_HAS_VALUE _FME_BLANK_STRING_'@Value(1stdaystart) @Value(1stmonthstart) To @Value(1stdayend) @Value(1stmonthend)'BOOL_OP;AND;COMPOSITE_TEST;<Unused>;TEST @Value(1stapplicableperiod) ATTRIBUTE_HAS_VALUE _FME_BLANK_STRING_'@Value(1stapplicableperiod)'FME_NUM_CONDITIONS4___
    -> AttributeCreator_20
AttributeCreator_20
    ATTR_TABLE = SET_TO 1stnamedperiods = FME_CONDITIONAL:DEFAULT_VALUE'@Value(period000)'BOOL_OP;OR;COMPOSITE_TEST;<Unused>;TEST @Value(period002) ATTRIBUTE_HAS_VALUE _FME_BLANK_STRING_'@Value(period000), @Value(period001), @Value(period002)'BOOL_OP;OR;COMPOSITE_TEST;<Unused>;TEST @Value(period001) ATTRIBUTE_HAS_VALUE _FME_BLANK_STRING_'@Value(period000), @Value(period001)'FME_NUM_CONDITIONS3___
    -> AttributeCreator_19
AttributeCreator_19
    ATTR_TABLE = SET_TO 1stnameddays = FME_CONDITIONAL:DEFAULT_VALUE'@Value(day000)'BOOL_OP;OR;COMPOSITE_TEST;<Unused>;TEST @Value(day006) ATTRIBUTE_HAS_VALUE _FME_BLANK_STRING_'@Value(day000) @Value(day001) @Value(day002) @Value(day003) @Value(day004) @Value(day005) @Value(day006)'BOOL_OP;OR;COMPOSITE_TEST;<Unused>;TEST @Value(day005) ATTRIBUTE_HAS_VALUE _FME_BLANK_STRING_'@Value(day000) @Value(day001) @Value(day002) @Value(day003) @Value(day004) @Value(day005)'BOOL_OP;OR;COMPOSITE_TEST;<Unused>;TEST @Value(day004) ATTRIBUTE_HAS_VALUE _FME_BLANK_STRING_'@Value(day000) @Value(day001) @Value(day002) @Value(day003) @Value(day004)'BOOL_OP;OR;COMPOSITE_TEST;<Unused>;TEST @Value(day003) ATTRIBUTE_HAS_VALUE _FME_BLANK_STRING_'@Value(day000) @Value(day001) @Value(day002) @Value(day003)'BOOL_OP;OR;COMPOSITE_TEST;<Unused>;TEST @Value(day002) ATTRIBUTE_HAS_VALUE _FME_BLANK_STRING_'@Value(day000) @Value(day001) @Value(day002)'BOOL_OP;OR;COMPOSITE_TEST;<Unused>;TEST @Value(day001) ATTRIBUTE_HAS_VALUE _FME_BLANK_STRING_'@Value(day000) @Value(day001)'FME_NUM_CONDITIONS7___
    -> AttributeCreator_33
AttributeCreator_33
    ATTR_TABLE = SET_TO 1stapplicableperiod = FME_CONDITIONAL:DEFAULT_VALUE''BOOL_OP;AND;COMPOSITE_TEST;<Unused>;TEST @Value(1stapplicableperiod) ATTRIBUTE_HAS_VALUE _FME_BLANK_STRING_;TEST @Value(1stnamedperiods) ATTRIBUTE_HAS_VALUE _FME_BLANK_STRING_;TEST @Value(1stnameddays) ATTRIBUTE_HAS_VALUE _FME_BLANK_STRING_'@Value(1stapplicableperiod) - @Value(1stnameddays), @Value(1stnamedperiods)'BOOL_OP;AND;COMPOSITE_TEST;<Unused>;TEST @Value(1stapplicableperiod) ATTRIBUTE_HAS_VALUE _FME_BLANK_STRING_;TEST @Value(1stnamedperiods) ATTRIBUTE_HAS_VALUE _FME_BLANK_STRING_'@Value(1stapplicableperiod) - @Value(1stnamedperiods)'BOOL_OP;AND;COMPOSITE_TEST;<Unused>;TEST @Value(1stapplicableperiod) ATTRIBUTE_HAS_VALUE _FME_BLANK_STRING_;TEST @Value(1stnameddays) ATTRIBUTE_HAS_VALUE _FME_BLANK_STRING_'@Value(1stapplicableperiod) - @Value(1stnameddays)'BOOL_OP;AND;COMPOSITE_TEST;<Unused>;TEST @Value(1stnamedperiods) ATTRIBUTE_HAS_VALUE _FME_BLANK_STRING_;TEST @Value(1stnameddays) ATTRIBUTE_HAS_VALUE _FME_BLANK_STRING_'@Value(1stnameddays), @Value(1stnamedperiods)'BOOL_OP;AND;COMPOSITE_TEST;<Unused>;TEST @Value(1stnamedperiods) ATTRIBUTE_HAS_VALUE _FME_BLANK_STRING_'@Value(1stnamedperiods)'BOOL_OP;AND;COMPOSITE_TEST;<Unused>;TEST @Value(1stnameddays) ATTRIBUTE_HAS_VALUE _FME_BLANK_STRING_'@Value(1stnameddays)'BOOL_OP;AND;COMPOSITE_TEST;<Unused>;TEST @Value(1stapplicableperiod) ATTRIBUTE_HAS_VALUE _FME_BLANK_STRING_'@Value(1stapplicableperiod)'FME_NUM_CONDITIONS8___
    -> AttributeCreator_27
AttributeCreator_27
    ATTR_TABLE = SET_TO 1stnamedtimes = FME_CONDITIONAL:DEFAULT_VALUE'@Value(time000)'BOOL_OP;OR;COMPOSITE_TEST;<Unused>;TEST @Value(time002) ATTRIBUTE_HAS_VALUE _FME_BLANK_STRING_'@Value(time000), @Value(time001), @Value(time002)'BOOL_OP;OR;COMPOSITE_TEST;<Unused>;TEST @Value(time001) ATTRIBUTE_HAS_VALUE _FME_BLANK_STRING_'@Value(time000), @Value(time001)'FME_NUM_CONDITIONS3___
    -> AttributeCreator_46
AttributeCreator_46
    ATTR_TABLE = SET_TO 1sttimerange = FME_CONDITIONAL:DEFAULT_VALUE''BOOL_OP;AND;COMPOSITE_TEST;<Unused>;TEST 1sttimestart3 NOT_ATTRIBUTE_IS_MISSING _FME_BLANK_STRING_;TEST 1sttimeend3 NOT_ATTRIBUTE_IS_MISSING _FME_BLANK_STRING_'@Value(1sttimestart0)-@Value(1sttimeend0) and @Value(1sttimestart1)-@Value(1sttimeend1) and @Value(1sttimestart2)-@Value(1sttimeend2) and @Value(1sttimestart3)-@Value(1sttimeend3)'BOOL_OP;AND;COMPOSITE_TEST;<Unused>;TEST 1sttimestart2 NOT_ATTRIBUTE_IS_MISSING _FME_BLANK_STRING_;TEST 1sttimeend2 NOT_ATTRIBUTE_IS_MISSING _FME_BLANK_STRING_'@Value(1sttimestart0)-@Value(1sttimeend0) and @Value(1sttimestart1)-@Value(1sttimeend1) and @Value(1sttimestart2)-@Value(1sttimeend2)'BOOL_OP;AND;COMPOSITE_TEST;<Unused>;TEST 1sttimestart1 NOT_ATTRIBUTE_IS_MISSING _FME_BLANK_STRING_;TEST 1sttimeend1 NOT_ATTRIBUTE_IS_MISSING _FME_BLANK_STRING_'@Value(1sttimestart0)-@Value(1sttimeend0) and @Value(1sttimestart1)-@Value(1sttimeend1)'BOOL_OP;AND;COMPOSITE_TEST;<Unused>;TEST 1sttimestart0 NOT_ATTRIBUTE_IS_MISSING _FME_BLANK_STRING_;TEST 1sttimeend0 NOT_ATTRIBUTE_IS_MISSING _FME_BLANK_STRING_'@Value(1sttimestart0)-@Value(1sttimeend0)'FME_NUM_CONDITIONS5___
    -> AttributeCreator_34
AttributeCreator_34
    ATTR_TABLE = SET_TO 1stapplicableperiod = FME_CONDITIONAL:DEFAULT_VALUE''BOOL_OP;AND;COMPOSITE_TEST;<Unused>;TEST @Value(1stapplicableperiod) ATTRIBUTE_HAS_VALUE _FME_BLANK_STRING_;TEST @Value(1stnamedtimes) ATTRIBUTE_HAS_VALUE _FME_BLANK_STRING_;TEST @Value(1sttimerange) ATTRIBUTE_HAS_VALUE _FME_BLANK_STRING_'@Value(1stapplicableperiod) @Value(1stnamedtimes) @Value(1sttimerange)'BOOL_OP;AND;COMPOSITE_TEST;<Unused>;TEST @Value(1stapplicableperiod) ATTRIBUTE_HAS_VALUE _FME_BLANK_STRING_;TEST @Value(1stnamedtimes) ATTRIBUTE_HAS_VALUE _FME_BLANK_STRING_'@Value(1stapplicableperiod) @Value(1stnamedtimes)'BOOL_OP;AND;COMPOSITE_TEST;<Unused>;TEST @Value(1stapplicableperiod) ATTRIBUTE_HAS_VALUE _FME_BLANK_STRING_;TEST @Value(1sttimerange) ATTRIBUTE_HAS_VALUE _FME_BLANK_STRING_'@Value(1stapplicableperiod) @Value(1sttimerange)'BOOL_OP;AND;COMPOSITE_TEST;<Unused>;TEST @Value(1stnamedtimes) ATTRIBUTE_HAS_VALUE _FME_BLANK_STRING_;TEST @Value(1sttimerange) ATTRIBUTE_HAS_VALUE _FME_BLANK_STRING_'@Value(1stnamedtimes) @Value(1sttimerange)'BOOL_OP;AND;COMPOSITE_TEST;<Unused>;TEST @Value(1stnamedtimes) ATTRIBUTE_HAS_VALUE _FME_BLANK_STRING_'@Value(1stnamedtimes)'BOOL_OP;AND;COMPOSITE_TEST;<Unused>;TEST @Value(1sttimerange) ATTRIBUTE_HAS_VALUE _FME_BLANK_STRING_'@Value(1sttimerange)'BOOL_OP;AND;COMPOSITE_TEST;<Unused>;TEST @Value(1stapplicableperiod) ATTRIBUTE_HAS_VALUE _FME_BLANK_STRING_'@Value(1stapplicableperiod)'FME_NUM_CONDITIONS8___
    -> AttributeCreator_22

Bookmark: Create applicable period 2
AttributeCreator_22
    ATTR_TABLE = SET_TO 2ndapplicableperiod = FME_CONDITIONAL:DEFAULT_VALUE'@Value(date100)'BOOL_OP;OR;COMPOSITE_TEST;<Unused>;TEST @Value(date102) ATTRIBUTE_HAS_VALUE _FME_BLANK_STRING_'@Value(date100), @Value(date101), @Value(date102)'BOOL_OP;OR;COMPOSITE_TEST;<Unused>;TEST @Value(date101) ATTRIBUTE_HAS_VALUE _FME_BLANK_STRING_'@Value(date100), @Value(date101)'FME_NUM_CONDITIONS3___
    -> AttributeCreator_9
AttributeCreator_9
    ATTR_TABLE = SET_TO 2ndapplicableperiod = FME_CONDITIONAL:DEFAULT_VALUE''BOOL_OP;AND;COMPOSITE_TEST;<Unused>;TEST @Value(2ndapplicableperiod) ATTRIBUTE_HAS_VALUE _FME_BLANK_STRING_;TEST @Value(2ndmonthstart) ATTRIBUTE_HAS_VALUE _FME_BLANK_STRING_'@Value(2ndapplicableperiod) - @Value(2nddaystart) @Value(2ndmonthstart) To @Value(2nddayend) @Value(2ndmonthend)'BOOL_OP;AND;COMPOSITE_TEST;<Unused>;TEST @Value(2ndmonthstart) ATTRIBUTE_HAS_VALUE _FME_BLANK_STRING_'@Value(2nddaystart) @Value(2ndmonthstart) To @Value(2nddayend) @Value(2ndmonthend)'BOOL_OP;AND;COMPOSITE_TEST;<Unused>;TEST @Value(2ndapplicableperiod) ATTRIBUTE_HAS_VALUE _FME_BLANK_STRING_'@Value(2ndapplicableperiod)'FME_NUM_CONDITIONS4___
    -> AttributeCreator_25
AttributeCreator_25
    ATTR_TABLE = SET_TO 2ndnamedperiods = FME_CONDITIONAL:DEFAULT_VALUE'@Value(period100)'BOOL_OP;OR;COMPOSITE_TEST;<Unused>;TEST @Value(period102) ATTRIBUTE_HAS_VALUE _FME_BLANK_STRING_'@Value(period100), @Value(period101), @Value(period102)'BOOL_OP;OR;COMPOSITE_TEST;<Unused>;TEST @Value(period101) ATTRIBUTE_HAS_VALUE _FME_BLANK_STRING_'@Value(period100), @Value(period101)'FME_NUM_CONDITIONS3___
    -> AttributeCreator_23
AttributeCreator_23
    ATTR_TABLE = SET_TO 2ndnameddays = FME_CONDITIONAL:DEFAULT_VALUE'@Value(day100)'BOOL_OP;OR;COMPOSITE_TEST;<Unused>;TEST @Value(day106) ATTRIBUTE_HAS_VALUE _FME_BLANK_STRING_'@Value(day100) @Value(day101) @Value(day102) @Value(day103) @Value(day104) @Value(day105) @Value(day106)'BOOL_OP;OR;COMPOSITE_TEST;<Unused>;TEST @Value(day105) ATTRIBUTE_HAS_VALUE _FME_BLANK_STRING_'@Value(day100) @Value(day101) @Value(day102) @Value(day103) @Value(day104) @Value(day105)'BOOL_OP;OR;COMPOSITE_TEST;<Unused>;TEST @Value(day104) ATTRIBUTE_HAS_VALUE _FME_BLANK_STRING_'@Value(day100) @Value(day101) @Value(day102) @Value(day103) @Value(day104)'BOOL_OP;OR;COMPOSITE_TEST;<Unused>;TEST @Value(day103) ATTRIBUTE_HAS_VALUE _FME_BLANK_STRING_'@Value(day100) @Value(day101) @Value(day102) @Value(day103)'BOOL_OP;OR;COMPOSITE_TEST;<Unused>;TEST @Value(day102) ATTRIBUTE_HAS_VALUE _FME_BLANK_STRING_'@Value(day100) @Value(day101) @Value(day102)'BOOL_OP;OR;COMPOSITE_TEST;<Unused>;TEST @Value(day101) ATTRIBUTE_HAS_VALUE _FME_BLANK_STRING_'@Value(day100) @Value(day101)'FME_NUM_CONDITIONS7___
    -> AttributeCreator_24
AttributeCreator_24
    ATTR_TABLE = SET_TO 2ndapplicableperiod = FME_CONDITIONAL:DEFAULT_VALUE''BOOL_OP;AND;COMPOSITE_TEST;<Unused>;TEST @Value(2ndapplicableperiod) ATTRIBUTE_HAS_VALUE _FME_BLANK_STRING_;TEST @Value(2ndnamedperiods) ATTRIBUTE_HAS_VALUE _FME_BLANK_STRING_;TEST @Value(2ndnameddays) ATTRIBUTE_HAS_VALUE _FME_BLANK_STRING_'@Value(2ndapplicableperiod) - @Value(2ndnameddays), @Value(2ndnamedperiods)'BOOL_OP;AND;COMPOSITE_TEST;<Unused>;TEST @Value(2ndapplicableperiod) ATTRIBUTE_HAS_VALUE _FME_BLANK_STRING_;TEST @Value(2ndnamedperiods) ATTRIBUTE_HAS_VALUE _FME_BLANK_STRING_'@Value(2ndapplicableperiod) - @Value(2ndnamedperiods)'BOOL_OP;AND;COMPOSITE_TEST;<Unused>;TEST @Value(2ndapplicableperiod) ATTRIBUTE_HAS_VALUE _FME_BLANK_STRING_;TEST @Value(2ndnameddays) ATTRIBUTE_HAS_VALUE _FME_BLANK_STRING_'@Value(2ndapplicableperiod) - @Value(2ndnameddays)'BOOL_OP;AND;COMPOSITE_TEST;<Unused>;TEST @Value(2ndnamedperiods) ATTRIBUTE_HAS_VALUE _FME_BLANK_STRING_;TEST @Value(2ndnameddays) ATTRIBUTE_HAS_VALUE _FME_BLANK_STRING_'@Value(2ndnameddays), @Value(2ndnamedperiods)'BOOL_OP;AND;COMPOSITE_TEST;<Unused>;TEST @Value(2ndnamedperiods) ATTRIBUTE_HAS_VALUE _FME_BLANK_STRING_'@Value(2ndnamedperiods)'BOOL_OP;AND;COMPOSITE_TEST;<Unused>;TEST @Value(2ndnameddays) ATTRIBUTE_HAS_VALUE _FME_BLANK_STRING_'@Value(2ndnameddays)'BOOL_OP;AND;COMPOSITE_TEST;<Unused>;TEST @Value(2ndapplicableperiod) ATTRIBUTE_HAS_VALUE _FME_BLANK_STRING_'@Value(2ndapplicableperiod)'FME_NUM_CONDITIONS8___
    -> AttributeCreator_28
AttributeCreator_28
    ATTR_TABLE = SET_TO 2ndnamedtimes = FME_CONDITIONAL:DEFAULT_VALUE'@Value(time100)'BOOL_OP;OR;COMPOSITE_TEST;<Unused>;TEST @Value(time102) ATTRIBUTE_HAS_VALUE _FME_BLANK_STRING_'@Value(time100), @Value(time101), @Value(time102)'BOOL_OP;OR;COMPOSITE_TEST;<Unused>;TEST @Value(time101) ATTRIBUTE_HAS_VALUE _FME_BLANK_STRING_'@Value(time100), @Value(time101)'FME_NUM_CONDITIONS3___
    -> AttributeCreator_43
AttributeCreator_43
    ATTR_TABLE = SET_TO 2ndtimerange = FME_CONDITIONAL:DEFAULT_VALUE''BOOL_OP;AND;COMPOSITE_TEST;<Unused>;TEST 2ndtimestart3 NOT_ATTRIBUTE_IS_MISSING _FME_BLANK_STRING_;TEST 2ndtimeend3 NOT_ATTRIBUTE_IS_MISSING _FME_BLANK_STRING_'@Value(2ndtimestart0)-@Value(2ndtimeend0) and @Value(2ndtimestart1)-@Value(2ndtimeend1) and @Value(2ndtimestart2)-@Value(2ndtimeend2) and @Value(2ndtimestart3)-@Value(2ndtimeend3)'BOOL_OP;AND;COMPOSITE_TEST;<Unused>;TEST 2ndtimestart2 NOT_ATTRIBUTE_IS_MISSING _FME_BLANK_STRING_;TEST 2ndtimeend2 NOT_ATTRIBUTE_IS_MISSING _FME_BLANK_STRING_'@Value(2ndtimestart0)-@Value(2ndtimeend0) and @Value(2ndtimestart1)-@Value(2ndtimeend1) and @Value(2ndtimestart2)-@Value(2ndtimeend2)'BOOL_OP;AND;COMPOSITE_TEST;<Unused>;TEST 2ndtimestart1 NOT_ATTRIBUTE_IS_MISSING _FME_BLANK_STRING_;TEST 2ndtimeend1 NOT_ATTRIBUTE_IS_MISSING _FME_BLANK_STRING_'@Value(2ndtimestart0)-@Value(2ndtimeend0) and @Value(2ndtimestart1)-@Value(2ndtimeend1)'BOOL_OP;AND;COMPOSITE_TEST;<Unused>;TEST 2ndtimestart0 NOT_ATTRIBUTE_IS_MISSING _FME_BLANK_STRING_;TEST 2ndtimeend0 NOT_ATTRIBUTE_IS_MISSING _FME_BLANK_STRING_'@Value(2ndtimestart0)-@Value(2ndtimeend0)'FME_NUM_CONDITIONS5___
    -> AttributeCreator_26
AttributeCreator_26
    ATTR_TABLE = SET_TO 2ndapplicableperiod = FME_CONDITIONAL:DEFAULT_VALUE''BOOL_OP;AND;COMPOSITE_TEST;<Unused>;TEST @Value(2ndapplicableperiod) ATTRIBUTE_HAS_VALUE _FME_BLANK_STRING_;TEST @Value(2ndnamedtimes) ATTRIBUTE_HAS_VALUE _FME_BLANK_STRING_;TEST @Value(2ndtimerange) ATTRIBUTE_HAS_VALUE _FME_BLANK_STRING_'@Value(2ndapplicableperiod) @Value(2ndnamedtimes) @Value(2ndtimerange)'BOOL_OP;AND;COMPOSITE_TEST;<Unused>;TEST @Value(2ndapplicableperiod) ATTRIBUTE_HAS_VALUE _FME_BLANK_STRING_;TEST @Value(2ndnamedtimes) ATTRIBUTE_HAS_VALUE _FME_BLANK_STRING_'@Value(2ndapplicableperiod) @Value(2ndnamedtimes)'BOOL_OP;AND;COMPOSITE_TEST;<Unused>;TEST @Value(2ndapplicableperiod) ATTRIBUTE_HAS_VALUE _FME_BLANK_STRING_;TEST @Value(2ndtimerange) ATTRIBUTE_HAS_VALUE _FME_BLANK_STRING_'@Value(2ndapplicableperiod) @Value(2ndtimerange)'BOOL_OP;AND;COMPOSITE_TEST;<Unused>;TEST @Value(2ndnamedtimes) ATTRIBUTE_HAS_VALUE _FME_BLANK_STRING_;TEST @Value(2ndtimerange) ATTRIBUTE_HAS_VALUE _FME_BLANK_STRING_'@Value(2ndnamedtimes) @Value(2ndtimerange)'BOOL_OP;AND;COMPOSITE_TEST;<Unused>;TEST @Value(2ndnamedtimes) ATTRIBUTE_HAS_VALUE _FME_BLANK_STRING_'@Value(2ndnamedtimes)'BOOL_OP;AND;COMPOSITE_TEST;<Unused>;TEST @Value(2ndtimerange) ATTRIBUTE_HAS_VALUE _FME_BLANK_STRING_'@Value(2ndtimerange)'BOOL_OP;AND;COMPOSITE_TEST;<Unused>;TEST @Value(2ndapplicableperiod) ATTRIBUTE_HAS_VALUE _FME_BLANK_STRING_'@Value(2ndapplicableperiod)'FME_NUM_CONDITIONS8___
    -> AttributeCreator_29

Bookmark: Create applicable period 3
AttributeCreator_29
    ATTR_TABLE = SET_TO 3rdapplicableperiod = FME_CONDITIONAL:DEFAULT_VALUE'@Value(date200)'BOOL_OP;OR;COMPOSITE_TEST;<Unused>;TEST @Value(date202) ATTRIBUTE_HAS_VALUE _FME_BLANK_STRING_'@Value(date200), @Value(date201), @Value(date202)'BOOL_OP;OR;COMPOSITE_TEST;<Unused>;TEST @Value(date201) ATTRIBUTE_HAS_VALUE _FME_BLANK_STRING_'@Value(date200), @Value(date201)'FME_NUM_CONDITIONS3___
    -> AttributeCreator_8
AttributeCreator_8
    ATTR_TABLE = SET_TO 3rdapplicableperiod = FME_CONDITIONAL:DEFAULT_VALUE''BOOL_OP;AND;COMPOSITE_TEST;<Unused>;TEST @Value(3rdapplicableperiod) ATTRIBUTE_HAS_VALUE _FME_BLANK_STRING_;TEST @Value(3rdmonthstart) ATTRIBUTE_HAS_VALUE _FME_BLANK_STRING_'@Value(3rdapplicableperiod) - @Value(3rddaystart) @Value(3rdmonthstart) To @Value(3rddayend) @Value(3rdmonthend)'BOOL_OP;AND;COMPOSITE_TEST;<Unused>;TEST @Value(3rdmonthstart) ATTRIBUTE_HAS_VALUE _FME_BLANK_STRING_'@Value(3rddaystart) @Value(3rdmonthstart) To @Value(3rddayend) @Value(3rdmonthend)'BOOL_OP;AND;COMPOSITE_TEST;<Unused>;TEST @Value(3rdapplicableperiod) ATTRIBUTE_HAS_VALUE _FME_BLANK_STRING_'@Value(3rdapplicableperiod)'FME_NUM_CONDITIONS4___
    -> AttributeCreator_36
AttributeCreator_36
    ATTR_TABLE = SET_TO 3rdnamedperiods = FME_CONDITIONAL:DEFAULT_VALUE'@Value(period200)'BOOL_OP;OR;COMPOSITE_TEST;<Unused>;TEST @Value(period202) ATTRIBUTE_HAS_VALUE _FME_BLANK_STRING_'@Value(period200), @Value(period201), @Value(period202)'BOOL_OP;OR;COMPOSITE_TEST;<Unused>;TEST @Value(period201) ATTRIBUTE_HAS_VALUE _FME_BLANK_STRING_'@Value(period200), @Value(period201)'FME_NUM_CONDITIONS3___
    -> AttributeCreator_31
AttributeCreator_31
    ATTR_TABLE = SET_TO 3rdnameddays = FME_CONDITIONAL:DEFAULT_VALUE'@Value(day200)'BOOL_OP;OR;COMPOSITE_TEST;<Unused>;TEST @Value(day206) ATTRIBUTE_HAS_VALUE _FME_BLANK_STRING_'@Value(day200) @Value(day201) @Value(day202) @Value(day203) @Value(day204) @Value(day205) @Value(day206)'BOOL_OP;OR;COMPOSITE_TEST;<Unused>;TEST @Value(day205) ATTRIBUTE_HAS_VALUE _FME_BLANK_STRING_'@Value(day200) @Value(day201) @Value(day202) @Value(day203) @Value(day204) @Value(day205)'BOOL_OP;OR;COMPOSITE_TEST;<Unused>;TEST @Value(day204) ATTRIBUTE_HAS_VALUE _FME_BLANK_STRING_'@Value(day200) @Value(day201) @Value(day202) @Value(day203) @Value(day204)'BOOL_OP;OR;COMPOSITE_TEST;<Unused>;TEST @Value(day203) ATTRIBUTE_HAS_VALUE _FME_BLANK_STRING_'@Value(day200) @Value(day201) @Value(day202) @Value(day203)'BOOL_OP;OR;COMPOSITE_TEST;<Unused>;TEST @Value(day202) ATTRIBUTE_HAS_VALUE _FME_BLANK_STRING_'@Value(day200) @Value(day201) @Value(day202)'BOOL_OP;OR;COMPOSITE_TEST;<Unused>;TEST @Value(day201) ATTRIBUTE_HAS_VALUE _FME_BLANK_STRING_'@Value(day200) @Value(day201)'FME_NUM_CONDITIONS7___
    -> AttributeCreator_35
AttributeCreator_35
    ATTR_TABLE = SET_TO 3rdapplicableperiod = FME_CONDITIONAL:DEFAULT_VALUE''BOOL_OP;AND;COMPOSITE_TEST;<Unused>;TEST @Value(3rdapplicableperiod) ATTRIBUTE_HAS_VALUE _FME_BLANK_STRING_;TEST @Value(3rdnamedperiods) ATTRIBUTE_HAS_VALUE _FME_BLANK_STRING_;TEST @Value(3rdnameddays) ATTRIBUTE_HAS_VALUE _FME_BLANK_STRING_'@Value(3rdapplicableperiod) - @Value(3rdnameddays), @Value(3rdnamedperiods)'BOOL_OP;AND;COMPOSITE_TEST;<Unused>;TEST @Value(3rdapplicableperiod) ATTRIBUTE_HAS_VALUE _FME_BLANK_STRING_;TEST @Value(3rdnamedperiods) ATTRIBUTE_HAS_VALUE _FME_BLANK_STRING_'@Value(3rdapplicableperiod) - @Value(3rdnamedperiods)'BOOL_OP;AND;COMPOSITE_TEST;<Unused>;TEST @Value(3rdapplicableperiod) ATTRIBUTE_HAS_VALUE _FME_BLANK_STRING_;TEST @Value(3rdnameddays) ATTRIBUTE_HAS_VALUE _FME_BLANK_STRING_'@Value(3rdapplicableperiod) - @Value(3rdnameddays)'BOOL_OP;AND;COMPOSITE_TEST;<Unused>;TEST @Value(3rdnamedperiods) ATTRIBUTE_HAS_VALUE _FME_BLANK_STRING_;TEST @Value(3rdnameddays) ATTRIBUTE_HAS_VALUE _FME_BLANK_STRING_'@Value(3rdnameddays), @Value(3rdnamedperiods)'BOOL_OP;AND;COMPOSITE_TEST;<Unused>;TEST @Value(3rdnamedperiods) ATTRIBUTE_HAS_VALUE _FME_BLANK_STRING_'@Value(3rdnamedperiods)'BOOL_OP;AND;COMPOSITE_TEST;<Unused>;TEST @Value(3rdnameddays) ATTRIBUTE_HAS_VALUE _FME_BLANK_STRING_'@Value(3rdnameddays)'BOOL_OP;AND;COMPOSITE_TEST;<Unused>;TEST @Value(3rdapplicableperiod) ATTRIBUTE_HAS_VALUE _FME_BLANK_STRING_'@Value(3rdapplicableperiod)'FME_NUM_CONDITIONS8___
    -> AttributeCreator_38
AttributeCreator_38
    ATTR_TABLE = SET_TO 3rdnamedtimes = FME_CONDITIONAL:DEFAULT_VALUE'@Value(time200)'BOOL_OP;OR;COMPOSITE_TEST;<Unused>;TEST @Value(time202) ATTRIBUTE_HAS_VALUE _FME_BLANK_STRING_'@Value(time200), @Value(time201), @Value(time202)'BOOL_OP;OR;COMPOSITE_TEST;<Unused>;TEST @Value(time201) ATTRIBUTE_HAS_VALUE _FME_BLANK_STRING_'@Value(time200), @Value(time201)'FME_NUM_CONDITIONS3___
    -> AttributeCreator_44
AttributeCreator_44
    ATTR_TABLE = SET_TO 3rdtimerange = FME_CONDITIONAL:DEFAULT_VALUE''BOOL_OP;AND;COMPOSITE_TEST;<Unused>;TEST 3rdtimestart3 NOT_ATTRIBUTE_IS_MISSING _FME_BLANK_STRING_;TEST 3rdtimeend3 NOT_ATTRIBUTE_IS_MISSING _FME_BLANK_STRING_'@Value(3rdtimestart0)-@Value(3rdtimeend0) and @Value(3rdtimestart1)-@Value(3rdtimeend1) and @Value(3rdtimestart2)-@Value(3rdtimeend2) and @Value(3rdtimestart3)-@Value(3rdtimeend3)'BOOL_OP;AND;COMPOSITE_TEST;<Unused>;TEST 3rdtimestart2 NOT_ATTRIBUTE_IS_MISSING _FME_BLANK_STRING_;TEST 3rdtimeend2 NOT_ATTRIBUTE_IS_MISSING _FME_BLANK_STRING_'@Value(3rdtimestart0)-@Value(3rdtimeend0) and @Value(3rdtimestart1)-@Value(3rdtimeend1) and @Value(3rdtimestart2)-@Value(3rdtimeend2)'BOOL_OP;AND;COMPOSITE_TEST;<Unused>;TEST 3rdtimestart1 NOT_ATTRIBUTE_IS_MISSING _FME_BLANK_STRING_;TEST 3rdtimeend1 NOT_ATTRIBUTE_IS_MISSING _FME_BLANK_STRING_'@Value(3rdtimestart0)-@Value(3rdtimeend0) and @Value(3rdtimestart1)-@Value(3rdtimeend1)'BOOL_OP;AND;COMPOSITE_TEST;<Unused>;TEST 3rdtimestart0 NOT_ATTRIBUTE_IS_MISSING _FME_BLANK_STRING_;TEST 3rdtimeend0 NOT_ATTRIBUTE_IS_MISSING _FME_BLANK_STRING_'@Value(3rdtimestart0)-@Value(3rdtimeend0)'FME_NUM_CONDITIONS5___
    -> AttributeCreator_37
AttributeCreator_37
    ATTR_TABLE = SET_TO 3rdapplicableperiod = FME_CONDITIONAL:DEFAULT_VALUE''BOOL_OP;AND;COMPOSITE_TEST;<Unused>;TEST @Value(3rdapplicableperiod) ATTRIBUTE_HAS_VALUE _FME_BLANK_STRING_;TEST @Value(3rdnamedtimes) ATTRIBUTE_HAS_VALUE _FME_BLANK_STRING_;TEST @Value(3rdtimerange) ATTRIBUTE_HAS_VALUE _FME_BLANK_STRING_'@Value(3rdapplicableperiod) @Value(3rdnamedtimes) @Value(3rdtimerange)'BOOL_OP;AND;COMPOSITE_TEST;<Unused>;TEST @Value(3rdapplicableperiod) ATTRIBUTE_HAS_VALUE _FME_BLANK_STRING_;TEST @Value(3rdnamedtimes) ATTRIBUTE_HAS_VALUE _FME_BLANK_STRING_'@Value(3rdapplicableperiod) @Value(3rdnamedtimes)'BOOL_OP;AND;COMPOSITE_TEST;<Unused>;TEST @Value(3rdapplicableperiod) ATTRIBUTE_HAS_VALUE _FME_BLANK_STRING_;TEST @Value(3rdtimerange) ATTRIBUTE_HAS_VALUE _FME_BLANK_STRING_'@Value(3rdapplicableperiod) @Value(3rdtimerange)'BOOL_OP;AND;COMPOSITE_TEST;<Unused>;TEST @Value(3rdnamedtimes) ATTRIBUTE_HAS_VALUE _FME_BLANK_STRING_;TEST @Value(3rdtimerange) ATTRIBUTE_HAS_VALUE _FME_BLANK_STRING_'@Value(3rdnamedtimes) @Value(3rdtimerange)'BOOL_OP;OR;COMPOSITE_TEST;<Unused>;TEST @Value(3rdnamedtimes) ATTRIBUTE_HAS_VALUE _FME_BLANK_STRING_'@Value(3rdnamedtimes)'BOOL_OP;OR;COMPOSITE_TEST;<Unused>;TEST @Value(3rdtimerange) ATTRIBUTE_HAS_VALUE _FME_BLANK_STRING_'@Value(3rdtimerange)'BOOL_OP;OR;COMPOSITE_TEST;<Unused>;TEST @Value(3rdapplicableperiod) ATTRIBUTE_HAS_VALUE _FME_BLANK_STRING_'@Value(3rdapplicableperiod)'FME_NUM_CONDITIONS8___
    -> AttributeCreator_32

Bookmark: Concatenate inclusion & exemption
AttributeCreator_32
    ATTR_TABLE:
      SET_TO ApplicablePeriod = FME_CONDITIONAL:DEFAULT_VALUE'@Value(1stapplicableperiod)'BOOL_OP;AND;COMPOSITE_TEST;<Unused>;TEST @Value(3rdapplicableperiod) ATTRIBUTE_HAS_VALUE _FME_BLANK_STRING_;TEST @Value(3rdapplicableperiod) != @Value(2ndapplicableperiod);TEST @Value(3rdapplicableperiod) != @Value(1stapplicableperiod)'@Value(1stapplicableperiod) | @Value(2ndapplicableperiod) | @Value(3rdapplicableperiod)'BOOL_OP;AND;COMPOSITE_TEST;<Unused>;TEST @Value(2ndapplicableperiod) ATTRIBUTE_HAS_VALUE _FME_BLANK_STRING_;TEST @Value(2ndapplicableperiod) != @Value(1stapplicableperiod)'@Value(1stapplicableperiod) | @Value(2ndapplicableperiod)'FME_NUM_CONDITIONS3___
      SET_TO NoOfNetworkLinks = 1
      SET_TO ChainOfNetworkLinks = FME_CONDITIONAL:DEFAULT_VALUE'1±@Value(RoadLink_TOID)'BOOL_OP;OR;COMPOSITE_TEST;<Unused>;TEST @Value(applicableDirection) = inDirection'1+@Value(RoadLink_TOID)'BOOL_OP;OR;COMPOSITE_TEST;<Unused>;TEST @Value(applicableDirection) = inOppositeDirection'1-@Value(RoadLink_TOID)'FME_NUM_CONDITIONS3___
    -> ListConcatenator_7
ListConcatenator_7
    DROP_EMPTY_PARTS = Yes
    LIST_ATTR = inclusion.VehicleQualifier.vehicle{}
    SEP = ", "
    VAL_ATTR = Inclusion_Vehicle
    -> ListConcatenator_8
ListConcatenator_8
    DROP_EMPTY_PARTS = Yes
    LIST_ATTR = inclusion.VehicleQualifier.use{}
    SEP = ", "
    VAL_ATTR = Inclusion_Use
    -> ListConcatenator_9
ListConcatenator_9
    DROP_EMPTY_PARTS = Yes
    LIST_ATTR = inclusion.VehicleQualifier.load{}
    SEP = ", "
    VAL_ATTR = Inclusion_Load
    -> AttributeCreator_14
AttributeCreator_14
    ATTR_TABLE = SET_TO Inclusion = FME_CONDITIONAL:DEFAULT_VALUE'_FME_NO_OP_'BOOL_OP;AND;COMPOSITE_TEST;<Unused>;TEST Inclusion_Vehicle ATTRIBUTE_HAS_A_VALUE _FME_BLANK_STRING_;TEST Inclusion_Use ATTRIBUTE_HAS_A_VALUE _FME_BLANK_STRING_;TEST Inclusion_Load ATTRIBUTE_HAS_A_VALUE _FME_BLANK_STRING_'Applying to: @Value(Inclusion_Vehicle), @Value(Inclusion_Use), @Value(Inclusion_Load)'BOOL_OP;AND;COMPOSITE_TEST;<Unused>;TEST Inclusion_Vehicle ATTRIBUTE_HAS_A_VALUE _FME_BLANK_STRING_;TEST Inclusion_Use ATTRIBUTE_HAS_A_VALUE _FME_BLANK_STRING_'Applying to: @Value(Inclusion_Vehicle), @Value(Inclusion_Use)'BOOL_OP;AND;COMPOSITE_TEST;<Unused>;TEST Inclusion_Vehicle ATTRIBUTE_HAS_A_VALUE _FME_BLANK_STRING_;TEST Inclusion_Load ATTRIBUTE_HAS_A_VALUE _FME_BLANK_STRING_'Applying to: @Value(Inclusion_Vehicle), @Value(Inclusion_Load)'BOOL_OP;AND;COMPOSITE_TEST;<Unused>;TEST Inclusion_Use ATTRIBUTE_HAS_A_VALUE _FME_BLANK_STRING_;TEST Inclusion_Load ATTRIBUTE_HAS_A_VALUE _FME_BLANK_STRING_'Applying to: @Value(Inclusion_Use), @Value(Inclusion_Load)'BOOL_OP;OR;COMPOSITE_TEST;<Unused>;TEST Inclusion_Vehicle ATTRIBUTE_HAS_A_VALUE _FME_BLANK_STRING_'Applying to: @Value(Inclusion_Vehicle)'BOOL_OP;OR;COMPOSITE_TEST;<Unused>;TEST Inclusion_Use ATTRIBUTE_HAS_A_VALUE _FME_BLANK_STRING_'Applying to: @Value(Inclusion_Use)'BOOL_OP;OR;COMPOSITE_TEST;<Unused>;TEST Inclusion_Load ATTRIBUTE_HAS_A_VALUE _FME_BLANK_STRING_'Applying to: @Value(Inclusion_Load)'FME_NUM_CONDITIONS8___
    -> ListConcatenator_10
ListConcatenator_10
    DROP_EMPTY_PARTS = Yes
    LIST_ATTR = exemption.VehicleQualifier.vehicle{}
    SEP = ", "
    VAL_ATTR = Exemption_Vehicle
    -> ListConcatenator_11
ListConcatenator_11
    DROP_EMPTY_PARTS = Yes
    LIST_ATTR = exemption.VehicleQualifier.use{}
    SEP = ", "
    VAL_ATTR = Exemption_Use
    -> ListConcatenator_12
ListConcatenator_12
    DROP_EMPTY_PARTS = Yes
    LIST_ATTR = exemption.VehicleQualifier.load{}
    SEP = ", "
    VAL_ATTR = Exemption_Load
    -> AttributeCreator_15
AttributeCreator_15
    ATTR_TABLE = SET_TO Exemption = FME_CONDITIONAL:DEFAULT_VALUE'_FME_NO_OP_'BOOL_OP;AND;COMPOSITE_TEST;<Unused>;TEST Exemption_Vehicle ATTRIBUTE_HAS_A_VALUE _FME_BLANK_STRING_;TEST Exemption_Use ATTRIBUTE_HAS_A_VALUE _FME_BLANK_STRING_;TEST Exemption_Load ATTRIBUTE_HAS_A_VALUE _FME_BLANK_STRING_'Except for: @Value(Exemption_Vehicle), @Value(Exemption_Use), @Value(Exemption_Load)'BOOL_OP;AND;COMPOSITE_TEST;<Unused>;TEST Exemption_Vehicle ATTRIBUTE_HAS_A_VALUE _FME_BLANK_STRING_;TEST Exemption_Use ATTRIBUTE_HAS_A_VALUE _FME_BLANK_STRING_'Except for: @Value(Exemption_Vehicle), @Value(Exemption_Use)'BOOL_OP;AND;COMPOSITE_TEST;<Unused>;TEST Exemption_Vehicle ATTRIBUTE_HAS_A_VALUE _FME_BLANK_STRING_;TEST Exemption_Load ATTRIBUTE_HAS_A_VALUE _FME_BLANK_STRING_'Except for: @Value(Exemption_Vehicle), @Value(Exemption_Load)'BOOL_OP;AND;COMPOSITE_TEST;<Unused>;TEST Exemption_Use ATTRIBUTE_HAS_A_VALUE _FME_BLANK_STRING_;TEST Exemption_Load ATTRIBUTE_HAS_A_VALUE _FME_BLANK_STRING_'Except for: @Value(Exemption_Use), @Value(Exemption_Load)'BOOL_OP;OR;COMPOSITE_TEST;<Unused>;TEST Exemption_Vehicle ATTRIBUTE_HAS_A_VALUE _FME_BLANK_STRING_'Except for: @Value(Exemption_Vehicle)'BOOL_OP;OR;COMPOSITE_TEST;<Unused>;TEST Exemption_Use ATTRIBUTE_HAS_A_VALUE _FME_BLANK_STRING_'Except for: @Value(Exemption_Use)'BOOL_OP;OR;COMPOSITE_TEST;<Unused>;TEST Exemption_Load ATTRIBUTE_HAS_A_VALUE _FME_BLANK_STRING_'Except for: @Value(Exemption_Load)'FME_NUM_CONDITIONS8___
    -> AttributeKeeper_5
AttributeKeeper_5
    KEEP_ATTRS = NoOfNetworkLinks,atPosition,Exemption,RoadLink_TOID,restriction,ApplicablePeriod,ChainOfNetworkLinks,applicableDirection,Inclusion,chunkname,TOID,beginLifespanVersion,identifier,reasonForChange,trafficSign,validFrom
    -> FeatureJoiner [LEFT]
    -> Bufferer

Bookmark: Create geometry
Bufferer
    ANGLE = 22.5
    CAP_STYLE = Round
    CORNER_STYLE = Round
    MODE = AREA
    OFFSET = 10
    BUFFERED -> Clipper [CLIPPER]
Clipper
    ATTR_ACCUM_MODE = Merge Clipper
    ATTR_CONFLICT_RES = Use Clipper
    BOUNDARY_CASES = Treat as Inside
    CLEANING_TOLERANCE = None
    CLIP_TYPE = Multiple Clippers
    CREATE_AGGREGATES = Yes
    GROUP_BY = TOID
    LINES_AS_SEGMENTS = No
    MEASURE_TYPE = Continuous
    MISSING_VAL_MODE = Compute
    PRESERVE_CLIPPEE_EXTENTS = No
    VAL_SOURCE = Clippee Only
    INSIDE -> AccessRestrictionLine (writer GEOPACKAGE_1)
    INSIDE -> DuplicateFilter
DuplicateFilter
    INPUT_ORDERED_CHOICE = No
    KEYATTR = RoadLink_TOID
    UNIQUE -> Snipper_3
    DUPLICATE -> DuplicateFilter_2
DuplicateFilter_2
    INPUT_ORDERED_CHOICE = No
    KEYATTR = RoadLink_TOID
    UNIQUE -> Snipper
    DUPLICATE -> Snipper_2
Snipper
    DEAGGREGATE_INPUT = YES
    ENDLOCATIONATTR = 25
    MEASUREMENTTYPE = 2D
    SNIPMODE = Distance (Percentage)
    STARTLOCATIONATTR = 25
    -> AccessRestrictionPoint (writer GEOPACKAGE_1)
Snipper_2
    DEAGGREGATE_INPUT = YES
    ENDLOCATIONATTR = 75
    MEASUREMENTTYPE = 2D
    SNIPMODE = Distance (Percentage)
    STARTLOCATIONATTR = 75
    -> AccessRestrictionPoint (writer GEOPACKAGE_1)
Snipper_3
    DEAGGREGATE_INPUT = YES
    ENDLOCATIONATTR = 50
    MEASUREMENTTYPE = 2D
    SNIPMODE = Distance (Percentage)
    STARTLOCATIONATTR = 50
    -> AccessRestrictionPoint (writer GEOPACKAGE_1)
AccessRestrictionPoint (writer GEOPACKAGE_1)
    attributes: TOID text(20), identifier text(16), restriction text(20), trafficSign text(120), ApplicablePeriod text(180), NoOfNetworkLinks smallint, ChainOfNetworkLinks text(190), Inclusion text(100), Exemption text(100), beginLifespanVersion text(20), reasonForChange text(32), validFrom text(20), chunkname text(50)
AccessRestrictionLine (writer GEOPACKAGE_1)
    attributes: TOID text(20), identifier text(16), restriction text(20), trafficSign text(120), formOfWay text(32), ApplicablePeriod text(180), NoOfNetworkLinks smallint, ChainOfNetworkLinks text(190), Inclusion text(100), Exemption text(100), beginLifespanVersion text(20), reasonForChange text(32), validFrom text(20), chunkname text(50)

Bookmark: vehicleQualifer.vehicle values have been exposed
ListExploder_5
    ATTR_ACCUM_MODE = Merge Incoming List
    ATTR_CONFLICT_RES = Use Original
    INDEX_ATTR = _element_index
    LIST_ATTR = exemption.VehicleQualifier.vehicle{}
    LIST_FOUND -> AttributeCreator_3
AttributeCreator_3
    ATTR_LIST = exemptionType,vehicle
    -> AttributeRenamer_3
AttributeRenamer_3
    ATTR_LIST = exemption.VehicleQualifier.vehicle,exemption,
    -> AccessRestriction_Exemption (writer GEOPACKAGE_1)

Bookmark: vehicleQualifer.load values have been exposed
ListExploder_2
    ATTR_ACCUM_MODE = Merge Incoming List
    ATTR_CONFLICT_RES = Use Original
    INDEX_ATTR = _element_index
    LIST_ATTR = exemption.VehicleQualifier.load{}
    LIST_FOUND -> AttributeCreator_4
AttributeCreator_4
    ATTR_LIST = exemptionType,load
    -> AttributeRenamer_5
AttributeRenamer_5
    ATTR_LIST = exemption.VehicleQualifier.load,exemption,
    -> AccessRestriction_Exemption (writer GEOPACKAGE_1)

Bookmark: Identifies the "exemption" "vehicleQualifer" attribute values which apply to any AccessRestriction
Note: The "exemption" attribute is populated by a vehicleQualifer data type. There are 3 attributes which contribute to the vehicleQualifer which are: / 1. Use / 2. Vehicle / 3. Load / Each of these 3 attributes have a multiplicity of 0..* so therefore need to be exposed to ensure all values populate the resulting table. This is carried out by the ListExploder transformer.
AccessRestriction_Exemption (writer GEOPACKAGE_1)
    attributes: TOID text(20), exemption text(50), exemptionType text(10)

Bookmark: vehicleQualifer.use values have been exposed
ListExploder_7
    ATTR_ACCUM_MODE = Merge Incoming List
    ATTR_CONFLICT_RES = Use Original
    INDEX_ATTR = _element_index
    LIST_ATTR = inclusion.VehicleQualifier.use{}
    LIST_FOUND -> AttributeCreator_7
AttributeCreator_7
    ATTR_LIST = inclusionType,use
    -> AttributeRenamer_9
AttributeRenamer_9
    ATTR_LIST = inclusion.VehicleQualifier.use,inclusion,
    -> AccessRestriction_Inclusion (writer GEOPACKAGE_1)

Bookmark: vehicleQualifer.vehicle values have been exposed
ListExploder_3
    ATTR_ACCUM_MODE = Merge Incoming List
    ATTR_CONFLICT_RES = Use Original
    INDEX_ATTR = _element_index
    LIST_ATTR = inclusion.VehicleQualifier.vehicle{}
    LIST_FOUND -> AttributeCreator_5
AttributeCreator_5
    ATTR_LIST = inclusionType,vehicle
    -> AttributeRenamer_7
AttributeRenamer_7
    ATTR_LIST = inclusion.VehicleQualifier.vehicle,inclusion,
    -> AccessRestriction_Inclusion (writer GEOPACKAGE_1)

Bookmark: vehicleQualifer.load values have been exposed
ListExploder_6
    ATTR_ACCUM_MODE = Merge Incoming List
    ATTR_CONFLICT_RES = Use Original
    INDEX_ATTR = _element_index
    LIST_ATTR = inclusion.VehicleQualifier.load{}
    LIST_FOUND -> AttributeCreator_6
AttributeCreator_6
    ATTR_LIST = inclusionType,load
    -> AttributeRenamer_8
AttributeRenamer_8
    ATTR_LIST = inclusion.VehicleQualifier.load,inclusion,
    -> AccessRestriction_Inclusion (writer GEOPACKAGE_1)

Bookmark: Identifies the "inclusion" "vehicleQualifer" attribute values which apply to any AccessRestriction
Note: The "inclusion" attribute is populated by a vehicleQualifer data type. There are 3 attributes which contribute to the vehicleQualifer which are: / 1. Use / 2.Vehicle / 3. Load / Each of these 3 attributes have a multiplicity of 0..* so therefore need to be exposed to ensure all values populate the resulting table. This is carried out by the ListExploder transformer.
AccessRestriction_Inclusion (writer GEOPACKAGE_1)
    attributes: TOID text(20), inclusion text(50), inclusionType text(10)

Bookmark: Time qualifiers
ListExploder_8
    ATTR_ACCUM_MODE = Merge Incoming List
    ATTR_CONFLICT_RES = Use Original
    INDEX_ATTR = _element_index
    LIST_ATTR = timeInterval{}
    LIST_FOUND -> AttributeRenamer_17
AttributeRenamer_17
    ATTR_TABLE = RENAME_SET_DEFAULT TOID > parentFeature_ID
    -> Counter
Note: Creates an identifier for date element
Counter
    CNT_ATTR = timeInterval_ID
    DOMAIN = counter
    SCOPE = Global
    START = 0
    -> ListExploder_9
    -> TQ_Parent_Date_Join (writer GEOPACKAGE_1)
    -> ListExploder_10
    -> ListExploder_11
ListExploder_11
    ATTR_ACCUM_MODE = Merge Incoming List
    ATTR_CONFLICT_RES = Use Original
    INDEX_ATTR = _element_index
    LIST_ATTR = TemporalPropertyType.dayPeriod{}
    LIST_FOUND -> Counter_2
Note: Creates an identifier for day element
Counter_2
    CNT_ATTR = dayPeriod_ID
    DOMAIN = counter
    SCOPE = Global
    START = 0
    -> ListExploder_12
    -> ListExploder_13
    -> ListExploder_14
    -> TQ_Date_Day_Join (writer GEOPACKAGE_1)
ListExploder_14
    ATTR_ACCUM_MODE = Merge Incoming List
    ATTR_CONFLICT_RES = Use Original
    INDEX_ATTR = _element_index
    LIST_ATTR = DayPropertyType.timePeriod{}
    LIST_FOUND -> Counter_3
Note: Creates an identifier for time element
Counter_3
    CNT_ATTR = timePeriod_ID
    DOMAIN = counter
    SCOPE = Global
    START = 0
    -> ListExploder_15
    -> ListExploder_16
    -> TQ_Day_Time_Join (writer GEOPACKAGE_1)

Bookmark: Date element
TQ_Parent_Date_Join (writer GEOPACKAGE_1)
    attributes: parentFeature_ID text(50), timeInterval_ID mediumint

Bookmark: DateRange
ListExploder_9
    ATTR_ACCUM_MODE = Merge Incoming List
    ATTR_CONFLICT_RES = Use Original
    INDEX_ATTR = _element_index
    LIST_ATTR = TemporalPropertyType.dateRange{}
    LIST_FOUND -> AttributeRenamer_6
AttributeRenamer_6
    ATTR_LIST = DateRangeType.startDate,startDate,,DateRangeType.endDate,endDate,,DateRangeType.startMonthDay,startMonthDay,,DateRangeType.endMonthDay,endMonthDay,
    -> DateFormatter_2
DateFormatter_2
    DATE_ATTR = endDate,startDate
    FMT = FME Date (%Y%m%d)
    INVALID_DATE_VALUE = _FME_NO_OP_
    SRCFMT = Unknown - Automatic Detection
    -> TQ_DateRange (writer GEOPACKAGE_1)
TQ_DateRange (writer GEOPACKAGE_1)
    attributes: parentFeature_ID text(50), timeInterval_ID mediumint, startDate text(20), endDate text(20), startMonthDay text(10), endMonthDay text(10)

Bookmark: NamedDate
ListExploder_10
    ATTR_ACCUM_MODE = Merge Incoming List
    ATTR_CONFLICT_RES = Use Original
    INDEX_ATTR = _element_index
    LIST_ATTR = TemporalPropertyType.namedDate{}
    LIST_FOUND -> AttributeRenamer_12
AttributeRenamer_12
    ATTR_LIST = TemporalPropertyType.namedDate,namedDate,
    -> TQ_NamedDate (writer GEOPACKAGE_1)
TQ_NamedDate (writer GEOPACKAGE_1)
    attributes: parentFeature_ID text(50), timeInterval_ID mediumint, namedDate text(20)

Bookmark: Day element
TQ_Date_Day_Join (writer GEOPACKAGE_1)
    attributes: parentFeature_ID text(50), timeInterval_ID mediumint, dayPeriod_ID mediumint

Bookmark: NamedDay
ListExploder_12
    ATTR_ACCUM_MODE = Merge Incoming List
    ATTR_CONFLICT_RES = Use Original
    INDEX_ATTR = _element_index
    LIST_ATTR = DayPropertyType.namedDay{}
    LIST_FOUND -> AttributeRenamer_13
AttributeRenamer_13
    ATTR_LIST = DayPropertyType.namedDay,namedDay,
    -> TQ_NamedDay (writer GEOPACKAGE_1)
TQ_NamedDay (writer GEOPACKAGE_1)
    attributes: parentFeature_ID text(50), timeInterval_ID mediumint, dayPeriod_ID mediumint, namedDay text(50)

Bookmark: NamedPeriod
ListExploder_13
    ATTR_ACCUM_MODE = Merge Incoming List
    ATTR_CONFLICT_RES = Use Original
    INDEX_ATTR = _element_index
    LIST_ATTR = DayPropertyType.namedPeriod{}
    LIST_FOUND -> AttributeRenamer_14
AttributeRenamer_14
    ATTR_LIST = DayPropertyType.namedPeriod,namedPeriod,
    -> TQ_NamedPeriod (writer GEOPACKAGE_1)
TQ_NamedPeriod (writer GEOPACKAGE_1)
    attributes: parentFeature_ID text(50), timeInterval_ID mediumint, dayPeriod_ID mediumint, namedPeriod text(50)

Bookmark: Time element
TQ_Day_Time_Join (writer GEOPACKAGE_1)
    attributes: parentFeature_ID text(50), timeInterval_ID mediumint, dayPeriod_ID mediumint, timePeriod_ID mediumint

Bookmark: TimeRange
ListExploder_15
    ATTR_ACCUM_MODE = Merge Incoming List
    ATTR_CONFLICT_RES = Use Original
    INDEX_ATTR = _element_index
    LIST_ATTR = TimePropertyType.timeRange{}
    LIST_FOUND -> AttributeRenamer_15
AttributeRenamer_15
    ATTR_LIST = TimeRangeType.startTime,startTime,,TimeRangeType.endTime,endTime,
    -> TQ_TimeRange (writer GEOPACKAGE_1)
TQ_TimeRange (writer GEOPACKAGE_1)
    attributes: parentFeature_ID text(50), timeInterval_ID mediumint, dayPeriod_ID mediumint, timePeriod_ID mediumint, startTime text(10), endTime text(10)

Bookmark: NamedTime
ListExploder_16
    ATTR_ACCUM_MODE = Merge Incoming List
    ATTR_CONFLICT_RES = Use Original
    INDEX_ATTR = _element_index
    LIST_ATTR = TimePropertyType.namedTime{}
    LIST_FOUND -> AttributeRenamer_16
AttributeRenamer_16
    ATTR_LIST = TimePropertyType.namedTime,namedTime,
    -> TQ_NamedTime (writer GEOPACKAGE_1)
TQ_NamedTime (writer GEOPACKAGE_1)
    attributes: parentFeature_ID text(50), timeInterval_ID mediumint, dayPeriod_ID mediumint, timePeriod_ID mediumint, namedTime text(50)

Bookmark: Add info from RoadLinks
RoadLink (reader GML_1)
    attributes: alternateIdentifier{}.ThematicIdentifier.identifier xml_char(20), alternateIdentifier{}.ThematicIdentifier.identifierScheme xml_char(39), alternateName{} xml_char(24), beginLifespanVersion xml_char(24), cycleFacility.CycleFacilityType.cycleFacility xml_char(39), cycleFacility.CycleFacilityType.cycleFacility.codeSpace xml_char(62), cycleFacility.CycleFacilityType.wholeLink xml_char(1), cycleFacility.CycleFacilityType.wholeLink.nilReason xml_char(8), cycleFacility.CycleFacilityType.wholeLink.xsi_nil xml_char(5), directionality.owns xml_char(6), directionality.xlink_href xml_char(76), elevationGain.ElevationGainType.inDirection xml_decimal(4,0), elevationGain.ElevationGainType.inDirection.uom xml_char(2), elevationGain.ElevationGainType.inOppositeDirection xml_decimal(4,0), elevationGain.ElevationGainType.inOppositeDirection.uom xml_char(2), endGradeSeparation xml_decimal(2,0), endNode.owns xml_char(6), endNode.xlink_href xml_char(22), fictitious xml_char(6), formOfWay xml_char(32), formsPartOf{}.owns xml_char(6), formsPartOf{}.xlink_href xml_char(22), inNetwork{}.owns xml_char(6), inNetwork{}.xlink_href xml_char(18), inspireId.Identifier.localId xml_decimal(17,0), inspireId.Identifier.namespace xml_char(19), length xml_decimal(7,2), length.uom xml_char(2), matchStatus xml_char(26), matchStatus.codeSpace xml_char(61),
      numberOfLanes{}.NumberOfLanesType.direction.owns xml_char(6), numberOfLanes{}.NumberOfLanesType.direction.xlink_href xml_char(76), numberOfLanes{}.NumberOfLanesType.minMaxNumberOfLanes xml_char(8), numberOfLanes{}.NumberOfLanesType.numberOfLanes xml_decimal(2,0), operationalState xml_char(5), operationalState.codeSpace xml_char(66), primaryRoute xml_char(6), provenance xml_char(16), provenance.codeSpace xml_char(66), reasonForChange xml_char(4), reasonForChange.codeSpace xml_char(47), relatedRoadArea{}.owns xml_char(6), relatedRoadArea{}.xlink_href xml_char(22), roadClassification xml_char(22), roadClassification.codeSpace xml_char(59), roadClassificationNumber xml_char(6), roadName{} xml_char(37), roadWidth.RoadWidthType.averageWidth xml_decimal(3,0), roadWidth.RoadWidthType.averageWidth.uom xml_char(2), roadWidth.RoadWidthType.confidenceLevel xml_decimal(2,0), roadWidth.RoadWidthType.minimumWidth xml_decimal(3,0), roadWidth.RoadWidthType.minimumWidth.uom xml_char(2), routeHierarchy xml_char(33), routeHierarchy.codeSpace xml_char(53), startGradeSeparation xml_decimal(2,0), startNode.owns xml_char(6), startNode.xlink_href xml_char(22), trunkRoad xml_char(6), validFrom xml_char(1), validFrom.nilReason xml_char(8),
      validFrom.xsi_nil xml_char(5), roadStructure xml_char(15)
    -> FeatureJoiner [RIGHT]
FeatureJoiner
    ATTR_CONFLICT_RES = Use Left
    GEOMETRY_HANDLING = Use Right
    JOIN_KEYS = RoadLink_TOID gml_id AUTO
    JOIN_MODE = Inner
    JOINED -> Clipper [CLIPPEE]
