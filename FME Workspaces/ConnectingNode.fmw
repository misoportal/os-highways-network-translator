FME workspace ConnectingNode.fmw

Parameters:
- SourceDataset_GML = $(PATHS_DATA_INPUT_FOLDER)\Highways_Path_ConnectingNode_*.gml*   # Source ConnectingNode GML File(s)
- DestDataset_GEOPACKAGE = $(MIDDLE_FOLDER)\ConnectingNode.gpkg   # Middle ConnectingNode Geopackage File

Readers:
- GML_1: GML from $(SourceDataset_GML)

Writers:
- GEOPACKAGE_1: GEOPACKAGE to $(DestDataset_GEOPACKAGE)

Note: Set input to local GML files
Note: Rename ID to TOID and other attributes to make easier to read
Note: Creates node geometry for connecting roadlinks and pathlinks
ConnectingNode (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, reasonForChange xml_buffer, reasonForChange.codeSpace xml_buffer, geometry xml_geometry, roadLink.nilReason xml_buffer, roadLink.gml_remoteSchema xml_buffer, roadLink.xlink_href xml_buffer, roadLink.owns xml_boolean, roadLink.xsi_nil xml_boolean
    -> AttributeRenamer
Note: Change output to prefered format
ConnectingNode (writer GEOPACKAGE_1)
    attributes: TOID text(20), identifier text(16), roadLink text(20), beginLifespanVersion text(20), reasonForChange text(32), chunkname text(50)

Bookmark: Create connectingNode
AttributeRenamer
    ATTR_TABLE:
      RENAME_SET_DEFAULT gml_id > TOID
      RENAME_SET_DEFAULT roadLink.xlink_href > roadLink
      RENAME_SET_DEFAULT fme_basename > chunkname
      RENAME_SET_DEFAULT inspireId.Identifier.localId > identifier
    -> DateFormatter
DateFormatter
    DATE_ATTR = beginLifespanVersion
    FMT = FME Date (%Y%m%d)
    INVALID_DATE_VALUE = FME_NULL_VALUE
    SRCFMT = Unknown - Automatic Detection
    -> StringReplacer
Note: Remove unwanted #
StringReplacer
    CASE = NO
    FIND_TEXT = #
    NO_MATCH = _FME_NO_OP_
    REGEXP = NO
    SRC_ATTRS = roadLink
    -> ConnectingNode (writer GEOPACKAGE_1)
