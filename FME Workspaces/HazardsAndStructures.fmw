FME workspace HazardsAndStructures.fmw

Parameters:
- SourceDataset_Hazard = $(ROADS_DATA_INPUT_FOLDER)\Highways_Rrami_Hazard_FULL_*.gml*   # Source Hazard GML File(s)
- SourceDataset_Structure = $(ROADS_DATA_INPUT_FOLDER)\Highways_Rrami_Structure_FULL_*.gml*   # Source Structure GML File(s)
- SourceDataset_RoadLink = $(ROADS_DATA_INPUT_FOLDER)\Highways_Rrami_RoadLink_FULL_*.gml*   # Source RoadLink GML File(s)
- DestDataset_HazardAndStructure = C:\OSMM_Highways\OS FreeSample\GPKG\HazardAndStructure.gpkg   # Middle HazardAndStructure Geopackage File

Readers:
- GML_1: GML from $(SourceDataset_RoadLink)
- GML_2: GML from $(SourceDataset_Hazard)
- GML_3: GML from $(SourceDataset_Structure)

Writers:
- GEOPACKAGE_1: GEOPACKAGE to $(DestDataset_HazardAndStructure)

Note: Set input to local GML files
Hazard (reader GML_2)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NodeReference.element.owns xml_boolean, networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer,
      networkRef{}.LinkReference.applicableDirection.xsi_nil xml_boolean, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean, networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean, networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer,
      networkRef{}.PointReference.offset.xsi_nil xml_boolean, networkRef{}.PointReference.atPositionGeometry xml_geometry, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64, networkRef{}.SimpleLinearReference.offset.nilReason xml_buffer, networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer,
      networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, hazard xml_buffer, hazard.codeSpace xml_buffer, description xml_buffer, reasonForChange xml_buffer, reasonForChange.codeSpace xml_buffer
    -> AttributeRenamer
Note: Rename id
AttributeRenamer
    ATTR_LIST = inspireId.Identifier.versionId,versionId,,inspireId.Identifier.localId,identifier,,gml_id,TOID,,fme_basename,chunkname,
    -> ListElementCounter_2
Note: Change to local input
Structure (reader GML_3)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NodeReference.element.owns xml_boolean, networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer,
      networkRef{}.LinkReference.applicableDirection.xsi_nil xml_boolean, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean, networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean, networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer,
      networkRef{}.PointReference.offset.xsi_nil xml_boolean, networkRef{}.PointReference.atPositionGeometry xml_geometry, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64, networkRef{}.SimpleLinearReference.offset.nilReason xml_buffer, networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer,
      networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, structure xml_buffer, structure.codeSpace xml_buffer, description xml_buffer, reasonForChange xml_buffer, reasonForChange.codeSpace xml_buffer
    -> AttributeRenamer_8
Note: Rename attributes
AttributeRenamer_8
    ATTR_LIST = inspireId.Identifier.namespace,identifierNamespace,,inspireId.Identifier.versionId,versionId,,inspireId.Identifier.localId,identifier,,gml_id,TOID,,fme_basename,chunkname,
    -> ListExploder_3
Structure_NetworkRef (writer GEOPACKAGE_1)
    attributes: TOID text(20), RoadLink_TOID text(20), RoadNode_TOID text(20), applicableDirection text(120), sequence mediumint, atPosition double, description text(120)

Bookmark: Work out the chain of network links
ListElementCounter_2
    CNT_ATTR = NoOfNetworkLinks
    LIST_NAME = networkRef{}
    -> ListConcatenator_7
    -> ListExploder
ListConcatenator_7
    DROP_EMPTY_PARTS = No
    LIST_ATTR = networkRef{}.LinkReference.applicableDirection.xlink_href
    SEP = ,
    VAL_ATTR = DirectionChain
    -> ListConcatenator_8
ListConcatenator_8
    DROP_EMPTY_PARTS = No
    LIST_ATTR = networkRef{}.LinkReference.element.xlink_href
    SEP = ,
    VAL_ATTR = LinkTOIDChain
    -> AttributeCreator_29
AttributeCreator_29
    ATTR_TABLE:
      SET_TO ChainOfNetworkLinks = FME_CONDITIONAL:DEFAULT_VALUE'_FME_NO_OP_'BOOL_OP;AND;COMPOSITE_TEST;<Unused>;TEST @Value(NoOfNetworkLinks) > 0;TEST @Substring(@Value(DirectionChain),@FindString(@Value(DirectionChain),"LinkDirectionValue/")+19,11) = inDirection'1+@Substring(@Value(LinkTOIDChain),1,20)'BOOL_OP;OR;COMPOSITE_TEST;<Unused>;TEST @Value(NoOfNetworkLinks) > 0'1-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_30
AttributeCreator_30
    ATTR_TABLE:
      SET_TO ChainOfNetworkLinks = FME_CONDITIONAL:DEFAULT_VALUE'_FME_NO_OP_'BOOL_OP;AND;COMPOSITE_TEST;<Unused>;TEST @Value(NoOfNetworkLinks) > 1;TEST @Substring(@Value(DirectionChain),@FindString(@Value(DirectionChain),"LinkDirectionValue/")+19,11) = inDirection'@Value(ChainOfNetworkLinks), 2+@Substring(@Value(LinkTOIDChain),1,20)'BOOL_OP;OR;COMPOSITE_TEST;<Unused>;TEST @Value(NoOfNetworkLinks) > 1'@Value(ChainOfNetworkLinks), 2-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_39
AttributeCreator_39
    ATTR_TABLE:
      SET_TO ChainOfNetworkLinks = FME_CONDITIONAL:DEFAULT_VALUE'_FME_NO_OP_'BOOL_OP;AND;COMPOSITE_TEST;<Unused>;TEST @Value(NoOfNetworkLinks) > 2;TEST @Substring(@Value(DirectionChain),@FindString(@Value(DirectionChain),"LinkDirectionValue/")+19,11) = inDirection'@Value(ChainOfNetworkLinks), 3+@Substring(@Value(LinkTOIDChain),1,20)'BOOL_OP;OR;COMPOSITE_TEST;<Unused>;TEST @Value(NoOfNetworkLinks) > 2'@Value(ChainOfNetworkLinks), 3-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_41
AttributeCreator_41
    ATTR_TABLE:
      SET_TO ChainOfNetworkLinks = FME_CONDITIONAL:DEFAULT_VALUE'_FME_NO_OP_'BOOL_OP;AND;COMPOSITE_TEST;<Unused>;TEST @Value(NoOfNetworkLinks) > 3;TEST @Substring(@Value(DirectionChain),@FindString(@Value(DirectionChain),"LinkDirectionValue/")+19,11) = inDirection'@Value(ChainOfNetworkLinks), 4+@Substring(@Value(LinkTOIDChain),1,20)'BOOL_OP;OR;COMPOSITE_TEST;<Unused>;TEST @Value(NoOfNetworkLinks) > 3'@Value(ChainOfNetworkLinks), 4-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_42
AttributeCreator_42
    ATTR_TABLE:
      SET_TO ChainOfNetworkLinks = FME_CONDITIONAL:DEFAULT_VALUE'_FME_NO_OP_'BOOL_OP;AND;COMPOSITE_TEST;<Unused>;TEST @Value(NoOfNetworkLinks) > 4;TEST @Substring(@Value(DirectionChain),@FindString(@Value(DirectionChain),"LinkDirectionValue/")+19,11) = inDirection'@Value(ChainOfNetworkLinks), 5+@Substring(@Value(LinkTOIDChain),1,20)'BOOL_OP;OR;COMPOSITE_TEST;<Unused>;TEST @Value(NoOfNetworkLinks) > 4'@Value(ChainOfNetworkLinks), 5-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_45
AttributeCreator_45
    ATTR_TABLE:
      SET_TO ChainOfNetworkLinks = FME_CONDITIONAL:DEFAULT_VALUE'_FME_NO_OP_'BOOL_OP;AND;COMPOSITE_TEST;<Unused>;TEST @Value(NoOfNetworkLinks) > 5;TEST @Substring(@Value(DirectionChain),@FindString(@Value(DirectionChain),"LinkDirectionValue/")+19,11) = inDirection'@Value(ChainOfNetworkLinks), 6+@Substring(@Value(LinkTOIDChain),1,20)'BOOL_OP;OR;COMPOSITE_TEST;<Unused>;TEST @Value(NoOfNetworkLinks) > 5'@Value(ChainOfNetworkLinks), 6-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_47
AttributeCreator_47
    ATTR_TABLE:
      SET_TO ChainOfNetworkLinks = FME_CONDITIONAL:DEFAULT_VALUE'_FME_NO_OP_'BOOL_OP;AND;COMPOSITE_TEST;<Unused>;TEST @Value(NoOfNetworkLinks) > 6;TEST @Substring(@Value(DirectionChain),@FindString(@Value(DirectionChain),"LinkDirectionValue/")+19,11) = inDirection'@Value(ChainOfNetworkLinks), 7+@Substring(@Value(LinkTOIDChain),1,20)'BOOL_OP;OR;COMPOSITE_TEST;<Unused>;TEST @Value(NoOfNetworkLinks) > 6'@Value(ChainOfNetworkLinks), 7-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> AttributeCreator_48
AttributeCreator_48
    ATTR_TABLE:
      SET_TO ChainOfNetworkLinks = FME_CONDITIONAL:DEFAULT_VALUE'_FME_NO_OP_'BOOL_OP;AND;COMPOSITE_TEST;<Unused>;TEST @Value(NoOfNetworkLinks) > 7;TEST @Substring(@Value(DirectionChain),@FindString(@Value(DirectionChain),"LinkDirectionValue/")+19,11) = inDirection'@Value(ChainOfNetworkLinks), 8+@Substring(@Value(LinkTOIDChain),1,20)'BOOL_OP;OR;COMPOSITE_TEST;<Unused>;TEST @Value(NoOfNetworkLinks) > 7'@Value(ChainOfNetworkLinks), 8-@Substring(@Value(LinkTOIDChain),1,20)'FME_NUM_CONDITIONS3___
      SET_TO DirectionChain = @Substring(@Value(DirectionChain),@FindString(@Value(DirectionChain),",")+1,2000)
      SET_TO LinkTOIDChain = @Substring(@Value(LinkTOIDChain),@FindString(@Value(LinkTOIDChain),",")+1,200)
    -> TestFilter_4
TestFilter_4
    DEFAULT_VALUE = <UNFILTERED>
    TEST_LIST = "BOOL_OP,OR,COMPOSITE_TEST,""""""<Unused>"""""",TEST_CLAUSE,TEST networkRef{0}.LinkReference.applicableDirection.xlink_href ATTRIBUTE_HAS_A_VALUE """,LinkReference
    LinkReference -> FeatureJoiner_2 [RIGHT]
    <UNFILTERED> -> TestFilter_6
FeatureJoiner_2
    ATTR_CONFLICT_RES = Use Left
    GEOMETRY_HANDLING = Use Left
    JOIN_KEYS = TOID TOID AUTO
    JOIN_MODE = Inner
    JOINED -> Bufferer
    JOINED -> TestFilter_6

Bookmark: Identifies the RoadLinks and RoadNodes a Hazard references
Note: Exploded list of the different / network references used by Hazards
ListExploder
    ATTR_ACCUM_MODE = Merge Incoming List
    ATTR_CONFLICT_RES = Use Original
    INDEX_ATTR = sequence
    LIST_ATTR = networkRef{}
    LIST_FOUND -> TestFilter
TestFilter
    DEFAULT_VALUE = <UNFILTERED>
    TEST_LIST = BOOL_OP,OR,COMPOSITE_TEST,<Unused>,TEST_CLAUSE,"TEST @Value(LinkReference.element.xlink_href) BEGINS_WITH #",LinkReference,BOOL_OP,OR,COMPOSITE_TEST,<Unused>,TEST_CLAUSE,"TEST @Value(PointReference.element.xlink_href) BEGINS_WITH #",PointReference,BOOL_OP,OR,COMPOSITE_TEST,<Unused>,TEST_CLAUSE,"TEST @Value(NodeReference.element.xlink_href) BEGINS_WITH #",NodeReference
    LinkReference -> AttributeRenamer_5
    PointReference -> AttributeRenamer_7
    NodeReference -> AttributeRenamer_6
Note: The Hazard feature type uses 3 types of Network Referencing: / 1. Link Referencing / 2. Node Referencing / 3. Point Referencing / This section identifies the type of Network Referencing used. / In addition, Node Referencing will reference the RoadLinks they affect. This has been seperated out into a seperate table in this workbench.
Hazard_NetworkRef (writer GEOPACKAGE_1)
    attributes: TOID text(20), RoadLink_TOID text(20), RoadNode_TOID text(20), applicableDirection text(120), sequence mediumint, atPosition double, description text(120)

Bookmark: Hazard features which reference the Linear Highway Network through Link Referencing
Note: Renaming the Link Reference / attribute and identifying the / sequence order the link referencing / applies in when there is more than / one Link Referenced.
AttributeRenamer_5
    ATTR_LIST = LinkReference.element.xlink_href,RoadLink_TOID,
    -> AttributeSplitter
Note: The attribute value for "directionality" is held as a / URL therefore to extract the value from the URL / the attribute needs splitting after every "/". This / action will create a list. The values after the last / "/" will contain the attribute value.
AttributeSplitter
    ATTR_NAME = LinkReference.applicableDirection.xlink_href
    DELIMITER = /
    DROP_EMPTY_PARTS = No
    LIST_NAME = _list
    TRIM_OPTION = Both
    -> AttributeRenamer_3
Note: Renaming the last list produced / by the AttributeSplitter which holds / the attribute value for the / "directionality" attribute.
AttributeRenamer_3
    ATTR_LIST = _list{5},applicableDirection,
    -> StringReplacer_2
Note: remove # from the / feature references
StringReplacer_2
    CASE = no
    FIND_TEXT = #
    NO_MATCH = _FME_NO_OP_
    REGEXP = no
    SRC_ATTRS = RoadLink_TOID
    -> Hazard_NetworkRef (writer GEOPACKAGE_1)
    -> FeatureJoiner [LEFT]

Bookmark: Hazard features which reference the Linear Highway Network through Point Referencing
AttributeRenamer_7
    ATTR_LIST = PointReference.element.xlink_href,RoadLink_TOID,
    -> AttributeSplitter_2
Note: The attribute value for "directionality" is held as a / URL therefore to extract the value from the URL / the attribute needs splitting after every "/". This / action will create a list. The values after the last / "/" will contain the attribute value.
AttributeSplitter_2
    ATTR_NAME = PointReference.applicableDirection.xlink_href
    DELIMITER = /
    DROP_EMPTY_PARTS = No
    LIST_NAME = _list
    TRIM_OPTION = Both
    -> AttributeRenamer_2
Note: Renaming the last list produced / by the AttributeSplitter which holds / the attribute value for the / "directionality" attribute.
AttributeRenamer_2
    ATTR_LIST = _list{5},applicableDirection,,PointReference.atPosition,atPosition,,PointReference.atPositionGeometry,atPositionGeometry,
    -> StringReplacer_3
Note: remove # from the / feature references
StringReplacer_3
    CASE = no
    FIND_TEXT = #
    NO_MATCH = _FME_NO_OP_
    REGEXP = no
    SRC_ATTRS = RoadLink_TOID
    -> Hazard_NetworkRef (writer GEOPACKAGE_1)

Bookmark: Hazard features which reference the Linear Highway Network through Node Referencing
AttributeRenamer_6
    ATTR_LIST = NodeReference.element.xlink_href,RoadNode_TOID,
    -> StringReplacer
Note: remove # from the / feature references
StringReplacer
    CASE = no
    FIND_TEXT = #
    NO_MATCH = _FME_NO_OP_
    REGEXP = no
    SRC_ATTRS = RoadNode_TOID
    -> ListExploder_2
    -> Hazard_NetworkRef (writer GEOPACKAGE_1)
Note: Features which use a Node Reference will also reference / the RoadLinks which they impact.Therefore, this list / exploder identifies the RoadLinks the Hazard feature / affects.
ListExploder_2
    ATTR_ACCUM_MODE = Merge Incoming List
    ATTR_CONFLICT_RES = Use Original
    INDEX_ATTR = _element_index
    LIST_ATTR = NodeReference.linkReference{}
    LIST_FOUND -> AttributeRenamer_4
AttributeRenamer_4
    ATTR_LIST = xlink_href,RoadLink_TOID,
    -> StringReplacer_4
Note: remove # from the / feature references
StringReplacer_4
    CASE = no
    FIND_TEXT = #
    NO_MATCH = _FME_NO_OP_
    REGEXP = no
    SRC_ATTRS = RoadLink_TOID
    -> Hazard_NodeReference_LinkReference (writer GEOPACKAGE_1)
Hazard_NodeReference_LinkReference (writer GEOPACKAGE_1)
    attributes: TOID text(20), RoadLink_TOID text(20)

Bookmark: miso processing - resolve LinkReference
RoadLink (reader GML_1)
    attributes: alternateIdentifier{}.ThematicIdentifier.identifier xml_char(20), alternateIdentifier{}.ThematicIdentifier.identifierScheme xml_char(39), alternateName{} xml_char(24), beginLifespanVersion xml_char(24), cycleFacility.CycleFacilityType.cycleFacility xml_char(39), cycleFacility.CycleFacilityType.cycleFacility.codeSpace xml_char(62), cycleFacility.CycleFacilityType.wholeLink xml_char(1), cycleFacility.CycleFacilityType.wholeLink.nilReason xml_char(8), cycleFacility.CycleFacilityType.wholeLink.xsi_nil xml_char(5), directionality.owns xml_char(6), directionality.xlink_href xml_char(76), elevationGain.ElevationGainType.inDirection xml_decimal(4,0), elevationGain.ElevationGainType.inDirection.uom xml_char(2), elevationGain.ElevationGainType.inOppositeDirection xml_decimal(4,0), elevationGain.ElevationGainType.inOppositeDirection.uom xml_char(2), endGradeSeparation xml_decimal(2,0), endNode.owns xml_char(6), endNode.xlink_href xml_char(22), fictitious xml_char(6), formOfWay xml_char(32), formsPartOf{}.owns xml_char(6), formsPartOf{}.xlink_href xml_char(22), inNetwork{}.owns xml_char(6), inNetwork{}.xlink_href xml_char(18), inspireId.Identifier.localId xml_decimal(17,0), inspireId.Identifier.namespace xml_char(19), length xml_decimal(7,2), length.uom xml_char(2), matchStatus xml_char(26), matchStatus.codeSpace xml_char(61),
      numberOfLanes{}.NumberOfLanesType.direction.owns xml_char(6), numberOfLanes{}.NumberOfLanesType.direction.xlink_href xml_char(76), numberOfLanes{}.NumberOfLanesType.minMaxNumberOfLanes xml_char(8), numberOfLanes{}.NumberOfLanesType.numberOfLanes xml_decimal(2,0), operationalState xml_char(5), operationalState.codeSpace xml_char(66), primaryRoute xml_char(6), provenance xml_char(16), provenance.codeSpace xml_char(66), reasonForChange xml_char(4), reasonForChange.codeSpace xml_char(47), relatedRoadArea{}.owns xml_char(6), relatedRoadArea{}.xlink_href xml_char(22), roadClassification xml_char(22), roadClassification.codeSpace xml_char(59), roadClassificationNumber xml_char(6), roadName{} xml_char(37), roadWidth.RoadWidthType.averageWidth xml_decimal(3,0), roadWidth.RoadWidthType.averageWidth.uom xml_char(2), roadWidth.RoadWidthType.confidenceLevel xml_decimal(2,0), roadWidth.RoadWidthType.minimumWidth xml_decimal(3,0), roadWidth.RoadWidthType.minimumWidth.uom xml_char(2), routeHierarchy xml_char(33), routeHierarchy.codeSpace xml_char(53), startGradeSeparation xml_decimal(2,0), startNode.owns xml_char(6), startNode.xlink_href xml_char(22), trunkRoad xml_char(6), validFrom xml_char(1), validFrom.nilReason xml_char(8),
      validFrom.xsi_nil xml_char(5), roadStructure xml_char(15)
    -> FeatureJoiner [RIGHT]
FeatureJoiner
    ATTR_CONFLICT_RES = Use Left
    GEOMETRY_HANDLING = Use Right
    JOIN_KEYS = RoadLink_TOID gml_id AUTO
    JOIN_MODE = Inner
    JOINED -> AttributeCreator_3
AttributeCreator_3
    ATTR_TABLE:
      SET_TO identifier = @Right(@Value(TOID),16)
      SET_TO laybyOrOneway = No
    -> TestFilter_3
TestFilter_3
    DEFAULT_VALUE = <UNFILTERED>
    TEST_LIST = "BOOL_OP,OR,COMPOSITE_TEST,""""""<Unused>"""""",TEST_CLAUSE,TEST hazard ATTRIBUTE_HAS_A_VALUE """,Hazard,"BOOL_OP,OR,COMPOSITE_TEST,""""""<Unused>"""""",TEST_CLAUSE,TEST structure ATTRIBUTE_HAS_A_VALUE """,Structure
    Hazard -> Clipper_2 [CLIPPEE]
    Hazard -> AttributeCreator
    Structure -> AttributeCreator_2
    Structure -> Snipper_2
AttributeCreator
    ATTR_TABLE:
      SET_TO laybyOrOneway = FME_CONDITIONAL:DEFAULT_VALUE'No'BOOL_OP;OR;COMPOSITE_TEST;<Unused>;TEST @Value(formOfWay) = Layby;TEST @Value(directionality.xlink_href) != http://inspire.ec.europa.eu/codelist/LinkDirectionValue/bothDirections'Yes'FME_NUM_CONDITIONS2___
      SET_TO singleLink = FME_CONDITIONAL:DEFAULT_VALUE'No'BOOL_OP;OR;COMPOSITE_TEST;<Unused>;TEST @Value(NoOfNetworkLinks) = 1'Yes'FME_NUM_CONDITIONS2___
    -> TestFilter_5
Note: Incl fudge for awkward ref
TestFilter_5
    DEFAULT_VALUE = <UNFILTERED>
    TEST_LIST:
      "BOOL_OP,OR,COMPOSITE_TEST,""""""<Unused>"""""",TEST_CLAUSE,TEST @Value(singleLink) = Yes
      TEST @Value(identifier) = 5000005223852992",SingleLink
    SingleLink -> Snipper
    <UNFILTERED> -> LineOnLineOverlayer [LINE]
LineOnLineOverlayer
    ATTRS_ACCUM_MODE = Use Attributes From One Feature
    CLEANING_TOLERANCE = 0.1
    DEAGGREGATE_INPUT = Yes
    GENERATE_LIST_DROP = NO
    GROUP_BY = TOID
    LOG_LEVEL = Limited
    SEPARATE_COLLINEAR_SEGMENTS = No
    POINT -> FeatureJoiner_2 [LEFT]
Snipper
    DEAGGREGATE_INPUT = YES
    ENDLOCATIONATTR = 50
    MEASUREMENTTYPE = 3D
    SNIPMODE = Distance (Percentage)
    STARTLOCATIONATTR = 50
    -> Bufferer
Bufferer
    CAP_STYLE = Round
    INTERP_SEGMENTS = 8
    OFFSET = 2.5
    BUFFERED -> Clipper_2 [CLIPPER]
Clipper_2
    ATTR_ACCUM_MODE = Only Use Clipper
    BOUNDARY_CASES = Treat as Inside
    CLEANING_TOLERANCE = None
    CLIP_TYPE = Multiple Clippers
    CREATE_AGGREGATES = Yes
    GROUP_BY = TOID
    LINES_AS_SEGMENTS = No
    MEASURE_TYPE = Continuous
    MISSING_VAL_MODE = Compute
    PRESERVE_CLIPPEE_EXTENTS = No
    VAL_SOURCE = Clippee Only
    INSIDE -> LineCombiner_3
LineCombiner_3
    ACCUM_ATTRS_NAME = Use Attributes From One Feature
    BREAK = no
    CONNECT_Z_MODE = First Wins
    CONSIDER_NODE_ELEVATION = no
    GROUP_BY = TOID
    LINES_AS_SEGMENTS = No
    PRESERVE = no
    TOPOLOGY = End noded
    LINE -> Advisory_RoadLink (writer GEOPACKAGE_1)
Snipper_2
    DEAGGREGATE_INPUT = YES
    ENDLOCATIONATTR = 40
    MEASUREMENTTYPE = 3D
    SNIPMODE = Distance (Percentage)
    STARTLOCATIONATTR = 40
    -> TestFilter_7
AttributeCreator_2
    ATTR_TABLE:
      SET_TO NoOfNetworkLinks = 1
      SET_TO ChainOfNetworkLinks = 1±@Value(RoadLink_TOID)
    -> Advisory_RoadLink (writer GEOPACKAGE_1)
Advisory_RoadLink (writer GEOPACKAGE_1)
    attributes: TOID text(20), identifier text(16), hazard text(50), structure text(50), description text(120), laybyOrOneway boolean, singleLink boolean, RoadLink_TOID text(32), NoOfNetworkLinks smallint, ChainOfNetworkLinks text(46), reasonForChange text(32), chunkname text(50)

Bookmark: Identifies the RoadLinks and RoadNodes a Structure references
Note: Exploded list of the different / network references used by Structures
Note: The Structure feature type uses 3 types of Network Referencing: / 1. Link Referencing / 2. Node Referencing / 3. Point Referencing / This section identifies the type of Network Referencing used. / In addition, Node Referencing will reference the RoadLinks they affect. This has been seperated out into a seperate table in this workbench.
ListExploder_3
    ATTR_ACCUM_MODE = Merge Incoming List
    ATTR_CONFLICT_RES = Use Original
    INDEX_ATTR = _element_index
    LIST_ATTR = networkRef{}
    LIST_FOUND -> TestFilter_2
TestFilter_2
    DEFAULT_VALUE = <UNFILTERED>
    TEST_LIST = BOOL_OP,OR,COMPOSITE_TEST,<Unused>,TEST_CLAUSE,"TEST @Value(LinkReference.element.xlink_href) BEGINS_WITH #",LinkReference,BOOL_OP,OR,COMPOSITE_TEST,<Unused>,TEST_CLAUSE,"TEST @Value(PointReference.element.xlink_href) BEGINS_WITH #",PointReference,BOOL_OP,OR,COMPOSITE_TEST,<Unused>,TEST_CLAUSE,"TEST @Value(NodeReference.element.xlink_href) BEGINS_WITH #",NodeReference
    LinkReference -> AttributeRenamer_10
    PointReference -> AttributeRenamer_12
    NodeReference -> AttributeRenamer_11

Bookmark: Structure features which reference the Linear Highway Network through Link Referencing
AttributeRenamer_10
    ATTR_LIST = LinkReference.element.xlink_href,RoadLink_TOID,
    -> AttributeSplitter_3
Note: The attribute value for "directionality" is held as a / URL therefore to extract the value from the URL / the attribute needs splitting after every "/". This / action will create a list. The values after the last / "/" will contain the attribute value.
AttributeSplitter_3
    ATTR_NAME = LinkReference.applicableDirection.xlink_href
    DELIMITER = /
    DROP_EMPTY_PARTS = No
    LIST_NAME = _list
    TRIM_OPTION = Both
    -> AttributeRenamer_9
Note: Renaming the last list produced / by the AttributeSplitter which holds / the attribute value for the / "directionality" attribute.
AttributeRenamer_9
    ATTR_LIST = _list{5},applicableDirection,
    -> StringReplacer_6
Note: remove # from the / feature references
StringReplacer_6
    CASE = no
    FIND_TEXT = #
    NO_MATCH = _FME_NO_OP_
    REGEXP = no
    SRC_ATTRS = RoadLink_TOID
    -> Structure_NetworkRef (writer GEOPACKAGE_1)
    -> FeatureJoiner [LEFT]

Bookmark: miso addition
TestFilter_6
    DEFAULT_VALUE = <UNFILTERED>
    TEST_LIST = "BOOL_OP,OR,COMPOSITE_TEST,""""""<Unused>"""""",TEST_CLAUSE,TEST validFrom ATTRIBUTE_HAS_A_VALUE """,ValidFrom
    ValidFrom -> DateFormatter_3
    <UNFILTERED> -> DateFormatter
DateFormatter_3
    DATE_ATTR = validFrom
    FMT = FME Date (%Y%m%d)
    INVALID_DATE_VALUE = _FME_NO_OP_
    SRCFMT = Unknown - Automatic Detection
    -> DateFormatter

Bookmark: Create Hazard feature
Note: Dates formatted as DMY
DateFormatter
    DATE_ATTR = beginLifespanVersion
    FMT = FME Date (%Y%m%d)
    INVALID_DATE_VALUE = _FME_NO_OP_
    SRCFMT = Unknown - Automatic Detection
    -> Hazard (writer GEOPACKAGE_1)
Note: This is an example output, writer will need to be added for specific output
Hazard (writer GEOPACKAGE_1)
    attributes: TOID text(20), identifier text(16), hazard text(50), description text(120), laybyOrOneway boolean, singleLink boolean, beginLifespanVersion text(20), reasonForChange text(32), validFrom text(20), validTo text(20), chunkname text(50)

Bookmark: Structure features which reference the Linear Highway Network through Point Referencing
AttributeRenamer_12
    ATTR_LIST = PointReference.element.xlink_href,RoadLink_TOID,,_element_index,sequence,
    -> AttributeSplitter_4
Note: The attribute value for "directionality" is held as a / URL therefore to extract the value from the URL / the attribute needs splitting after every "/". This / action will create a list. The values after the last / "/" will contain the attribute value.
AttributeSplitter_4
    ATTR_NAME = PointReference.applicableDirection.xlink_href
    DELIMITER = /
    DROP_EMPTY_PARTS = No
    LIST_NAME = _list
    TRIM_OPTION = Both
    -> AttributeRenamer_13
Note: Renaming the last list produced / by the AttributeSplitter which holds / the attribute value for the / "directionality" attribute.
AttributeRenamer_13
    ATTR_LIST = _list{5},applicableDirection,,PointReference.atPosition,atPosition,,PointReference.atPositionGeometry,atPositionGeometry,
    -> StringReplacer_7
Note: remove # from the / feature references
StringReplacer_7
    CASE = no
    FIND_TEXT = #
    NO_MATCH = _FME_NO_OP_
    REGEXP = no
    SRC_ATTRS = RoadLink_TOID
    -> Structure_NetworkRef (writer GEOPACKAGE_1)
    -> TestFilter_7

Bookmark: Structure features which reference the Linear Highway Network through Node Referencing
AttributeRenamer_11
    ATTR_LIST = NodeReference.element.xlink_href,RoadNode_TOID,
    -> StringReplacer_5
Note: remove # from the / feature references
StringReplacer_5
    CASE = no
    FIND_TEXT = #
    NO_MATCH = _FME_NO_OP_
    REGEXP = no
    SRC_ATTRS = RoadNode_TOID
    -> ListExploder_4
    -> Structure_NetworkRef (writer GEOPACKAGE_1)
    -> TestFilter_7
Note: Features which use a Node Reference will also reference / the RoadLinks which they impact.Therefore, this list / exploder identifies the RoadLinks the Strucutre feature / affects.
ListExploder_4
    ATTR_ACCUM_MODE = Merge Incoming List
    ATTR_CONFLICT_RES = Use Original
    INDEX_ATTR = _element_index
    LIST_ATTR = NodeReference.linkReference{}
    LIST_FOUND -> AttributeRenamer_14
AttributeRenamer_14
    ATTR_LIST = xlink_href,RoadLink_TOID,
    -> StringReplacer_8
Note: remove # from the / feature references
StringReplacer_8
    CASE = no
    FIND_TEXT = #
    NO_MATCH = _FME_NO_OP_
    REGEXP = no
    SRC_ATTRS = RoadLink_TOID
    -> Structure_NodeReference_LinkReference (writer GEOPACKAGE_1)
Structure_NodeReference_LinkReference (writer GEOPACKAGE_1)
    attributes: TOID text(20), RoadLink_TOID text(20)

Bookmark: miso addition
TestFilter_7
    DEFAULT_VALUE = <UNFILTERED>
    TEST_LIST = "BOOL_OP,OR,COMPOSITE_TEST,""""""<Unused>"""""",TEST_CLAUSE,TEST validFrom ATTRIBUTE_HAS_A_VALUE """,ValidFrom
    ValidFrom -> DateFormatter_4
    <UNFILTERED> -> DateFormatter_2
DateFormatter_4
    DATE_ATTR = validFrom
    FMT = FME Date (%Y%m%d)
    INVALID_DATE_VALUE = _FME_NO_OP_
    SRCFMT = Unknown - Automatic Detection
    -> DateFormatter_2

Bookmark: Create Structure feature
Note: Format as DMY
DateFormatter_2
    DATE_ATTR = beginLifespanVersion
    FMT = FME Date (%Y%m%d)
    INVALID_DATE_VALUE = _FME_NO_OP_
    SRCFMT = Unknown - Automatic Detection
    -> Structure (writer GEOPACKAGE_1)
Note: This is an example output, writer will need to be added for specific output
Structure (writer GEOPACKAGE_1)
    attributes: TOID text(20), identifier text(37), structure text(50), description text(120), beginLifespanVersion text(20), reasonForChange text(32), validFrom text(20), validTo text(20), chunkname text(50)
