FME workspace RestrictionForVehicles.fmw

Parameters:
- SourceDataset_GML = $(ROADS_DATA_INPUT_FOLDER)\Highways_Rrami_RestrictionForVehicles_FULL_*.gml*   # Source RestrictionForVehicles GML File(s)
- DestDataset_GEOPACKAGE = $(MIDDLE_FOLDER)\VehicleRestriction.gpkg   # Destination VehicleRestriction Geopackage File
- SourceDataset_RoadLink = $(ROADS_DATA_INPUT_FOLDER)\Highways_Rrami_RoadLink_FULL_*.gml*   # Source RoadLink GML File(s)

Readers:
- GML_1: GML from $(SourceDataset_RoadLink)
- GML_2: GML from $(SourceDataset_GML)

Writers:
- GEOPACKAGE_1: GEOPACKAGE to $(DestDataset_GEOPACKAGE)

Note: Change to local input
RestrictionForVehicles (reader GML_2)
    attributes: networkRef{}.nilReason xml_buffer, networkRef{}.xsi_nil xml_boolean, networkRef{}.NetworkReference.element.owns xml_boolean, networkRef{}.NetworkReference.element.nilReason xml_buffer, networkRef{}.NetworkReference.element.gml_remoteSchema xml_buffer, networkRef{}.NetworkReference.element.xlink_href xml_buffer, networkRef{}.LinkReference.element.owns xml_boolean, networkRef{}.LinkReference.element.nilReason xml_buffer, networkRef{}.LinkReference.element.gml_remoteSchema xml_buffer, networkRef{}.LinkReference.element.xlink_href xml_buffer, networkRef{}.LinkReference.applicableDirection.owns xml_boolean, networkRef{}.LinkReference.applicableDirection.nilReason xml_buffer, networkRef{}.LinkReference.applicableDirection.gml_remoteSchema xml_buffer, networkRef{}.LinkReference.applicableDirection.xlink_href xml_buffer, networkRef{}.LinkReference.applicableDirection.xsi_nil xml_boolean, networkRef{}.SimpleLinearReference.element.owns xml_boolean, networkRef{}.SimpleLinearReference.element.nilReason xml_buffer, networkRef{}.SimpleLinearReference.element.gml_remoteSchema xml_buffer, networkRef{}.SimpleLinearReference.element.xlink_href xml_buffer, networkRef{}.SimpleLinearReference.applicableDirection.owns xml_boolean, networkRef{}.SimpleLinearReference.applicableDirection.nilReason xml_buffer, networkRef{}.SimpleLinearReference.applicableDirection.gml_remoteSchema xml_buffer, networkRef{}.SimpleLinearReference.applicableDirection.xlink_href xml_buffer, networkRef{}.SimpleLinearReference.applicableDirection.xsi_nil xml_boolean, networkRef{}.SimpleLinearReference.fromPosition xml_real64, networkRef{}.SimpleLinearReference.fromPosition.uom xml_buffer, networkRef{}.SimpleLinearReference.toPosition xml_real64, networkRef{}.SimpleLinearReference.toPosition.uom xml_buffer, networkRef{}.SimpleLinearReference.offset xml_real64, networkRef{}.SimpleLinearReference.offset.nilReason xml_buffer,
      networkRef{}.SimpleLinearReference.offset.uom xml_buffer, networkRef{}.SimpleLinearReference.offset.xsi_nil xml_boolean, networkRef{}.LinearReference.element.owns xml_boolean, networkRef{}.LinearReference.element.nilReason xml_buffer, networkRef{}.LinearReference.element.gml_remoteSchema xml_buffer, networkRef{}.LinearReference.element.xlink_href xml_buffer, networkRef{}.LinearReference.applicableDirection.owns xml_boolean, networkRef{}.LinearReference.applicableDirection.nilReason xml_buffer, networkRef{}.LinearReference.applicableDirection.gml_remoteSchema xml_buffer, networkRef{}.LinearReference.applicableDirection.xlink_href xml_buffer, networkRef{}.LinearReference.applicableDirection.xsi_nil xml_boolean, networkRef{}.LinearReference.fromPosition xml_real64, networkRef{}.LinearReference.fromPosition.uom xml_buffer, networkRef{}.LinearReference.toPosition xml_real64, networkRef{}.LinearReference.toPosition.uom xml_buffer, networkRef{}.LinearReference.offset xml_real64, networkRef{}.LinearReference.offset.nilReason xml_buffer, networkRef{}.LinearReference.offset.uom xml_buffer, networkRef{}.LinearReference.offset.xsi_nil xml_boolean, networkRef{}.LinearReference.fromPositionGeometry xml_geometry, networkRef{}.LinearReference.toPositionGeometry xml_geometry, networkRef{}.SimplePointReference.element.owns xml_boolean, networkRef{}.SimplePointReference.element.nilReason xml_buffer, networkRef{}.SimplePointReference.element.gml_remoteSchema xml_buffer, networkRef{}.SimplePointReference.element.xlink_href xml_buffer, networkRef{}.SimplePointReference.applicableDirection.owns xml_boolean, networkRef{}.SimplePointReference.applicableDirection.nilReason xml_buffer, networkRef{}.SimplePointReference.applicableDirection.gml_remoteSchema xml_buffer, networkRef{}.SimplePointReference.applicableDirection.xlink_href xml_buffer, networkRef{}.SimplePointReference.applicableDirection.xsi_nil xml_boolean,
      networkRef{}.SimplePointReference.atPosition xml_real64, networkRef{}.SimplePointReference.atPosition.uom xml_buffer, networkRef{}.SimplePointReference.offset xml_real64, networkRef{}.SimplePointReference.offset.nilReason xml_buffer, networkRef{}.SimplePointReference.offset.uom xml_buffer, networkRef{}.SimplePointReference.offset.xsi_nil xml_boolean, networkRef{}.PointReference.element.owns xml_boolean, networkRef{}.PointReference.element.nilReason xml_buffer, networkRef{}.PointReference.element.gml_remoteSchema xml_buffer, networkRef{}.PointReference.element.xlink_href xml_buffer, networkRef{}.PointReference.applicableDirection.owns xml_boolean, networkRef{}.PointReference.applicableDirection.nilReason xml_buffer, networkRef{}.PointReference.applicableDirection.gml_remoteSchema xml_buffer, networkRef{}.PointReference.applicableDirection.xlink_href xml_buffer, networkRef{}.PointReference.applicableDirection.xsi_nil xml_boolean, networkRef{}.PointReference.atPosition xml_real64, networkRef{}.PointReference.atPosition.uom xml_buffer, networkRef{}.PointReference.offset xml_real64, networkRef{}.PointReference.offset.nilReason xml_buffer, networkRef{}.PointReference.offset.uom xml_buffer, networkRef{}.PointReference.offset.xsi_nil xml_boolean, networkRef{}.PointReference.atPositionGeometry xml_geometry, networkRef{}.NetworkReferenceLocation.element.owns xml_boolean, networkRef{}.NetworkReferenceLocation.element.nilReason xml_buffer, networkRef{}.NetworkReferenceLocation.element.gml_remoteSchema xml_buffer, networkRef{}.NetworkReferenceLocation.element.xlink_href xml_buffer, networkRef{}.NetworkReferenceLocation.locationDescription xml_buffer, networkRef{}.NetworkReferenceLocation.locationStart xml_geometry, networkRef{}.NetworkReferenceLocation.locationEnd xml_geometry, networkRef{}.NodeReference.element.owns xml_boolean,
      networkRef{}.NodeReference.element.nilReason xml_buffer, networkRef{}.NodeReference.element.gml_remoteSchema xml_buffer, networkRef{}.NodeReference.element.xlink_href xml_buffer, networkRef{}.NodeReference.location xml_geometry, networkRef{}.NodeReference.linkReference{}.nilReason xml_buffer, networkRef{}.NodeReference.linkReference{}.gml_remoteSchema xml_buffer, networkRef{}.NodeReference.linkReference{}.xlink_href xml_buffer, networkRef{}.NodeReference.linkReference{}.owns xml_boolean, inspireId.Identifier.localId xml_buffer, inspireId.Identifier.namespace xml_buffer, inspireId.Identifier.versionId xml_buffer, inspireId.Identifier.versionId.nilReason xml_buffer, inspireId.Identifier.versionId.xsi_nil xml_boolean, beginLifespanVersion xml_datetime, beginLifespanVersion.nilReason xml_buffer, beginLifespanVersion.xsi_nil xml_boolean, endLifespanVersion xml_datetime, endLifespanVersion.nilReason xml_buffer, endLifespanVersion.xsi_nil xml_boolean, validFrom xml_datetime, validFrom.nilReason xml_buffer, validFrom.xsi_nil xml_boolean, validTo xml_datetime, validTo.nilReason xml_buffer, validTo.xsi_nil xml_boolean, measure xml_real64, measure.uom xml_buffer, restrictionType.owns xml_boolean, restrictionType.nilReason xml_buffer, restrictionType.gml_remoteSchema xml_buffer,
      restrictionType.xlink_href xml_buffer, exemption.VehicleQualifier.use{} xml_char(7), exemption.VehicleQualifier.use{}.codeSpace xml_char(57), measure2 xml_decimal(4,0), measure2.uom xml_char(3), reasonForChange xml_char(33), reasonForChange.codeSpace xml_char(51), sourceOfMeasure xml_char(11), structure xml_char(18), structure.codeSpace xml_char(63), trafficSign{} xml_char(75)
    -> AttributeRenamer
Note: There are currently no vehicle qualifiers of vehicle or load, as a result FME cannot find the attributes, the ListExploder's have been disabled
Note: Rename attributes
AttributeRenamer
    ATTR_LIST = inspireId.Identifier.localId,identifier,,inspireId.Identifier.versionId,versionId,,measure.uom,measure_uom,,measure2.uom,measure2_uom,,locationDescripton,locationDescription,,locationDescripton.xml_lang,locationDescription_lang,,trafficRegulationOrder.TrafficRegulationOrderType.trafficRegulationOrder,trafficRegulationOrder,,trafficRegulationOrder.TrafficRegulationOrderType.troDescription,troDescription,,gml_id,TOID,,fme_basename,chunkname,
    -> TestFilter_2
    -> ListExploder_3
    -> ListExploder_2 [off]
    -> ListExploder_4 [off]
    -> ListExploder_5 [off]
    -> ListExploder_7
    -> ListExploder_6 [off]

Bookmark: miso addition
TestFilter_2
    DEFAULT_VALUE = <UNFILTERED>
    TEST_LIST = "BOOL_OP,OR,COMPOSITE_TEST,""""""<Unused>"""""",TEST_CLAUSE,TEST validFrom ATTRIBUTE_HAS_A_VALUE """,ValidFrom
    ValidFrom -> DateFormatter_2
    <UNFILTERED> -> DateFormatter
DateFormatter_2
    DATE_ATTR = validFrom
    FMT = FME Date (%Y%m%d)
    INVALID_DATE_VALUE = _FME_NO_OP_
    SRCFMT = Unknown - Automatic Detection
    -> DateFormatter

Bookmark: Create RestrictionForVehicles feature
Note: Format dates as DMY
Note: Split traffic signals into 2 attributes as the multiplicity is 1..2.
DateFormatter
    DATE_ATTR = beginLifespanVersion
    FMT = FME Date (%Y%m%d)
    INVALID_DATE_VALUE = _FME_NO_OP_
    SRCFMT = Unknown - Automatic Detection
    -> ListIndexer
Note: The attribute value for "restrcitionType" is held as a / URL therefore to extract the value from the URL / the attribute needs splitting after every "/". This / action will create a list. The values after the last / "/" will contain the attribute value.
AttributeSplitter
    ATTR_NAME = restrictionType.xlink_href
    DELIMITER = /
    DROP_EMPTY_PARTS = No
    LIST_NAME = _list
    TRIM_OPTION = Both
    -> AttributeRenamer_11
Note: Renaming the last list produced by the / AttributeSplitter which holds the attribute / value for the "restrictionType" attribute.
Note: This is an example output, writer will need to be added for specific output
AttributeRenamer_11
    ATTR_LIST = _list{5},restrictionType,
    -> AttributeValueMapper

Bookmark: Traffic Sign 1
ListIndexer
    INDEX = 0
    LIST_ATTR = trafficSign{}
    PREFIX = trafficSign1_
    -> AttributeRenamer_2
AttributeRenamer_2
    ATTR_LIST = trafficSign1_trafficSign,trafficSign1,
    -> ListIndexer_2

Bookmark: Traffic Sign 2
ListIndexer_2
    INDEX = 1
    LIST_ATTR = trafficSign{}
    PREFIX = trafficSign2_
    -> AttributeRenamer_3
AttributeRenamer_3
    ATTR_LIST = trafficSign2_trafficSign,trafficSign2,
    -> AttributeSplitter

Bookmark: miso addition
AttributeValueMapper
    DEFAULT_VALUE = Vehicle restriction
    DIRECTION = Forward (Source To Destination)
    LUT = maximumDoubleAxleWeight,Weight limit 2 axles,maximumHeight,Height limit,maximumLength,Length limit,maximumSingleAxleWeight,Weight limit 1 axle,maximumTotalWeight,Weight limit - total,maximumTripleAxleWeight,Weight limit 3 axles,maximumWidth,Width limit,maximumUnladenWeight,Weight limit unladen
    SRC = restrictionType
    VAL_ATTR = restrictionType
    -> ListExploder

Bookmark: Identifies the RoadLinks and RoadNodes a RestrictionForVehicle references
ListExploder
    ATTR_ACCUM_MODE = Merge Incoming List
    ATTR_CONFLICT_RES = Use Original
    INDEX_ATTR = _element_index
    LIST_ATTR = networkRef{}
    LIST_FOUND -> TestFilter
TestFilter
    DEFAULT_VALUE = <UNFILTERED>
    TEST_LIST = BOOL_OP,OR,COMPOSITE_TEST,<Unused>,TEST_CLAUSE,"TEST @Value(PointReference.element.xlink_href) BEGINS_WITH #",PointReference,BOOL_OP,OR,COMPOSITE_TEST,<Unused>,TEST_CLAUSE,"TEST @Value(NodeReference.element.xlink_href) BEGINS_WITH #",NodeReference
    PointReference -> AttributeRenamer_12
    NodeReference -> AttributeRenamer_7
Note: The RestrictionForVehicle feature type uses 2 types of Network Referencing: / 1. Node Referencing / 2. Point Referencing / This section identifies the type of Network Referencing used. / In addition, Node Referencing will reference the RoadLinks they affect. This has been seperated out into a seperate table in this workbench.
RestrictionForVehicles_NetworkRef (writer GEOPACKAGE_1)
    attributes: TOID text(20), RoadNode_TOID text(20), RoadLink_TOID text(20), applicableDirection text(120), atPosition double

Bookmark: RestrictionForVehicle features which reference the Linear Highway Network through Point Referencing
AttributeRenamer_12
    ATTR_LIST = PointReference.element.xlink_href,RoadLink_TOID,
    -> AttributeSplitter_2
Note: The attribute value for "directionality" is held as a / URL therefore to extract the value from the URL / the attribute needs splitting after every "/". This / action will create a list. The values after the last / "/" will contain the attribute value.
AttributeSplitter_2
    ATTR_NAME = PointReference.applicableDirection.xlink_href
    DELIMITER = /
    DROP_EMPTY_PARTS = No
    LIST_NAME = _list
    TRIM_OPTION = Both
    -> AttributeRenamer_13
Note: Renaming the last list produced / by the AttributeSplitter which holds / the attribute value for the / "directionality" attribute.
AttributeRenamer_13
    ATTR_LIST = _list{5},applicableDirection,,PointReference.atPosition,atPosition,,PointReference.atPositionGeometry,atPositionGeometry,
    -> StringReplacer_2
Note: remove # from the / feature references
StringReplacer_2
    CASE = no
    FIND_TEXT = #
    NO_MATCH = _FME_NO_OP_
    REGEXP = no
    SRC_ATTRS = RoadLink_TOID
    -> RestrictionForVehicles_NetworkRef (writer GEOPACKAGE_1)
    -> AttributeCreator_4

Bookmark: RestrictionForVehicle features which reference the Linear Highway Network through Node Referencing
AttributeRenamer_7
    ATTR_LIST = NodeReference.element.xlink_href,RoadNode_TOID,
    -> StringReplacer
Note: remove # from the / feature references
StringReplacer
    CASE = no
    FIND_TEXT = #
    NO_MATCH = _FME_NO_OP_
    REGEXP = no
    SRC_ATTRS = RoadNode_TOID
    -> ListExploder_8
    -> RestrictionForVehicles_NetworkRef (writer GEOPACKAGE_1)
Note: Features which use a Node Reference will also reference / the RoadLinks which they impact.Therefore, this list / exploder identifies the RoadLinks the RestrictionForVehicle / feature affects.
ListExploder_8
    ATTR_ACCUM_MODE = Merge Incoming List
    ATTR_CONFLICT_RES = Use Original
    INDEX_ATTR = _element_index
    LIST_ATTR = NodeReference.linkReference{}
    LIST_FOUND -> AttributeRenamer_14
AttributeRenamer_14
    ATTR_LIST = xlink_href,RoadLink_TOID,
    -> StringReplacer_4
Note: remove # from the / feature references
StringReplacer_4
    CASE = no
    FIND_TEXT = #
    NO_MATCH = _FME_NO_OP_
    REGEXP = no
    SRC_ATTRS = RoadLink_TOID
    -> RestrictionForVehicles_NodeReference_LinkReference (writer GEOPACKAGE_1)
    -> AttributeCreator_4
RestrictionForVehicles_NodeReference_LinkReference (writer GEOPACKAGE_1)
    attributes: TOID text(20), RoadLink_TOID text(20)

Bookmark: Concatenate inclusion & exemption
AttributeCreator_4
    ATTR_TABLE:
      SET_TO NoOfNetworkLinks = 1
      SET_TO applicableDirection = FME_CONDITIONAL:DEFAULT_VALUE'bothDIrections'BOOL_OP;OR;COMPOSITE_TEST;<Unused>;TEST applicableDirection ATTRIBUTE_HAS_A_VALUE _FME_BLANK_STRING_'_FME_NO_OP_'FME_NUM_CONDITIONS2___
      SET_TO ChainOfNetworkLinks = FME_CONDITIONAL:DEFAULT_VALUE'1±@Value(RoadLink_TOID)'BOOL_OP;OR;COMPOSITE_TEST;<Unused>;TEST @Value(applicableDirection) = inDirection'1+@Value(RoadLink_TOID)'BOOL_OP;OR;COMPOSITE_TEST;<Unused>;TEST @Value(applicableDirection) = inOppositeDirection'1-@Value(RoadLink_TOID)'FME_NUM_CONDITIONS3___
    -> ListConcatenator_7
ListConcatenator_7
    DROP_EMPTY_PARTS = Yes
    LIST_ATTR = inclusion.VehicleQualifier.vehicle{}
    SEP = ", "
    VAL_ATTR = Inclusion_Vehicle
    -> ListConcatenator_8
ListConcatenator_8
    DROP_EMPTY_PARTS = Yes
    LIST_ATTR = inclusion.VehicleQualifier.use{}
    SEP = ", "
    VAL_ATTR = Inclusion_Use
    -> ListConcatenator_9
ListConcatenator_9
    DROP_EMPTY_PARTS = Yes
    LIST_ATTR = inclusion.VehicleQualifier.load{}
    SEP = ", "
    VAL_ATTR = Inclusion_Load
    -> AttributeCreator_14
AttributeCreator_14
    ATTR_TABLE = SET_TO Inclusion = FME_CONDITIONAL:DEFAULT_VALUE'_FME_NO_OP_'BOOL_OP;AND;COMPOSITE_TEST;<Unused>;TEST Inclusion_Vehicle ATTRIBUTE_HAS_A_VALUE _FME_BLANK_STRING_;TEST Inclusion_Use ATTRIBUTE_HAS_A_VALUE _FME_BLANK_STRING_;TEST Inclusion_Load ATTRIBUTE_HAS_A_VALUE _FME_BLANK_STRING_'Applying to: @Value(Inclusion_Vehicle), @Value(Inclusion_Use), @Value(Inclusion_Load)'BOOL_OP;AND;COMPOSITE_TEST;<Unused>;TEST Inclusion_Vehicle ATTRIBUTE_HAS_A_VALUE _FME_BLANK_STRING_;TEST Inclusion_Use ATTRIBUTE_HAS_A_VALUE _FME_BLANK_STRING_'Applying to: @Value(Inclusion_Vehicle), @Value(Inclusion_Use)'BOOL_OP;AND;COMPOSITE_TEST;<Unused>;TEST Inclusion_Vehicle ATTRIBUTE_HAS_A_VALUE _FME_BLANK_STRING_;TEST Inclusion_Load ATTRIBUTE_HAS_A_VALUE _FME_BLANK_STRING_'Applying to: @Value(Inclusion_Vehicle), @Value(Inclusion_Load)'BOOL_OP;AND;COMPOSITE_TEST;<Unused>;TEST Inclusion_Use ATTRIBUTE_HAS_A_VALUE _FME_BLANK_STRING_;TEST Inclusion_Load ATTRIBUTE_HAS_A_VALUE _FME_BLANK_STRING_'Applying to: @Value(Inclusion_Use), @Value(Inclusion_Load)'BOOL_OP;OR;COMPOSITE_TEST;<Unused>;TEST Inclusion_Vehicle ATTRIBUTE_HAS_A_VALUE _FME_BLANK_STRING_'Applying to: @Value(Inclusion_Vehicle)'BOOL_OP;OR;COMPOSITE_TEST;<Unused>;TEST Inclusion_Use ATTRIBUTE_HAS_A_VALUE _FME_BLANK_STRING_'Applying to: @Value(Inclusion_Use)'BOOL_OP;OR;COMPOSITE_TEST;<Unused>;TEST Inclusion_Load ATTRIBUTE_HAS_A_VALUE _FME_BLANK_STRING_'Applying to: @Value(Inclusion_Load)'FME_NUM_CONDITIONS8___
    -> ListConcatenator_10
ListConcatenator_10
    DROP_EMPTY_PARTS = Yes
    LIST_ATTR = exemption.VehicleQualifier.vehicle{}
    SEP = ", "
    VAL_ATTR = Exemption_Vehicle
    -> ListConcatenator_11
ListConcatenator_11
    DROP_EMPTY_PARTS = Yes
    LIST_ATTR = exemption.VehicleQualifier.use{}
    SEP = ", "
    VAL_ATTR = Exemption_Use
    -> ListConcatenator_12
ListConcatenator_12
    DROP_EMPTY_PARTS = Yes
    LIST_ATTR = exemption.VehicleQualifier.load{}
    SEP = ", "
    VAL_ATTR = Exemption_Load
    -> AttributeCreator_15
AttributeCreator_15
    ATTR_TABLE = SET_TO Exemption = FME_CONDITIONAL:DEFAULT_VALUE'_FME_NO_OP_'BOOL_OP;AND;COMPOSITE_TEST;<Unused>;TEST Exemption_Vehicle ATTRIBUTE_HAS_A_VALUE _FME_BLANK_STRING_;TEST Exemption_Use ATTRIBUTE_HAS_A_VALUE _FME_BLANK_STRING_;TEST Exemption_Load ATTRIBUTE_HAS_A_VALUE _FME_BLANK_STRING_'Except for: @Value(Exemption_Vehicle), @Value(Exemption_Use), @Value(Exemption_Load)'BOOL_OP;AND;COMPOSITE_TEST;<Unused>;TEST Exemption_Vehicle ATTRIBUTE_HAS_A_VALUE _FME_BLANK_STRING_;TEST Exemption_Use ATTRIBUTE_HAS_A_VALUE _FME_BLANK_STRING_'Except for: @Value(Exemption_Vehicle), @Value(Exemption_Use)'BOOL_OP;AND;COMPOSITE_TEST;<Unused>;TEST Exemption_Vehicle ATTRIBUTE_HAS_A_VALUE _FME_BLANK_STRING_;TEST Exemption_Load ATTRIBUTE_HAS_A_VALUE _FME_BLANK_STRING_'Except for: @Value(Exemption_Vehicle), @Value(Exemption_Load)'BOOL_OP;AND;COMPOSITE_TEST;<Unused>;TEST Exemption_Use ATTRIBUTE_HAS_A_VALUE _FME_BLANK_STRING_;TEST Exemption_Load ATTRIBUTE_HAS_A_VALUE _FME_BLANK_STRING_'Except for: @Value(Exemption_Use), @Value(Exemption_Load)'BOOL_OP;OR;COMPOSITE_TEST;<Unused>;TEST Exemption_Vehicle ATTRIBUTE_HAS_A_VALUE _FME_BLANK_STRING_'Except for: @Value(Exemption_Vehicle)'BOOL_OP;OR;COMPOSITE_TEST;<Unused>;TEST Exemption_Use ATTRIBUTE_HAS_A_VALUE _FME_BLANK_STRING_'Except for: @Value(Exemption_Use)'BOOL_OP;OR;COMPOSITE_TEST;<Unused>;TEST Exemption_Load ATTRIBUTE_HAS_A_VALUE _FME_BLANK_STRING_'Except for: @Value(Exemption_Load)'FME_NUM_CONDITIONS8___
    -> AttributeKeeper_5
AttributeKeeper_5
    KEEP_ATTRS = trafficSign1,troDescription,trafficRegulationOrder,measure,chunkname,Exemption,TOID,beginLifespanVersion,measure_uom,NoOfNetworkLinks,ChainOfNetworkLinks,Inclusion,RoadLink_TOID,measure2_uom,structure,applicableDirection,identifier,trafficSign2,validFrom,sourceOfMeasure,measure2,reasonForChange,restrictionType
    -> PointOnLineOverlayer [POINT]
    -> FeatureJoiner [LEFT]

Bookmark: vehicleQualifer.use values have been exposed
ListExploder_3
    ATTR_ACCUM_MODE = Merge Incoming List
    ATTR_CONFLICT_RES = Use Original
    INDEX_ATTR = _element_index
    LIST_ATTR = exemption.VehicleQualifier.use{}
    LIST_FOUND -> AttributeCreator_2
AttributeCreator_2
    ATTR_LIST = exemptionType,use
    -> AttributeRenamer_5
AttributeRenamer_5
    ATTR_LIST = ExemptionType.use,exemption,
    -> RestrictionForVehicles_Exemption (writer GEOPACKAGE_1)

Bookmark: vehicleQualifer.vehicle values have been exposed
ListExploder_4 [off]
    ATTR_ACCUM_MODE = Merge Incoming List
    ATTR_CONFLICT_RES = Use Original
    INDEX_ATTR = _element_index
    LIST_ATTR = exemption.VehicleQualifier.vehicle{}
    LIST_FOUND -> AttributeCreator_3
AttributeCreator_3
    ATTR_LIST = exemptionType,vehicle
    -> AttributeRenamer_6
AttributeRenamer_6
    ATTR_LIST = ExemptionType.vehicle,exemption,
    -> RestrictionForVehicles_Exemption (writer GEOPACKAGE_1)

Bookmark: vehicleQualifer.load values have been exposed
ListExploder_2 [off]
    ATTR_ACCUM_MODE = Merge Incoming List
    ATTR_CONFLICT_RES = Use Original
    INDEX_ATTR = _element_index
    LIST_ATTR = exemption.VehicleQualifier.load{}
    LIST_FOUND -> AttributeCreator
AttributeCreator
    ATTR_LIST = exemptionType,load
    -> AttributeRenamer_4
AttributeRenamer_4
    ATTR_LIST = ExemptionType.load,exemption,
    -> RestrictionForVehicles_Exemption (writer GEOPACKAGE_1)

Bookmark: Identifies the "exemption" "vehicleQualifer" attribute values which apply to any RestrictionForVehicles - Disabled
Note: The "exemption" attribute is populated by a vehicleQualifer data type. There are 3 attributes which contribute to the vehicleQualifer which are: / 1. Use / 2.Vehicle / 3. Load / Each of these 3 attributes have a multiplicity of 0..* so therefore need to be exposed to ensure all values populate the resulting table. This is carried out by the ListExploder transformer. / The link to this process has been disabled as there are currently no expemtions available in the product for RestrictionForVehicle features.
RestrictionForVehicles_Exemption (writer GEOPACKAGE_1)
    attributes: TOID text(20), exemption text(50), exemptionType text(10)

Bookmark: vehicleQualifer.use values have been exposed
ListExploder_7
    ATTR_ACCUM_MODE = Merge Incoming List
    ATTR_CONFLICT_RES = Use Original
    INDEX_ATTR = _element_index
    LIST_ATTR = exemption.VehicleQualifier.use{}
    LIST_FOUND -> AttributeCreator_7
AttributeCreator_7
    ATTR_LIST = inclusionType,use
    -> AttributeRenamer_10
AttributeRenamer_10
    ATTR_LIST = inclusion.VehicleQualifier.use,inclusion,
    -> RestrictionForVehicles_Inclusion (writer GEOPACKAGE_1)

Bookmark: vehicleQualifer.vehicle values have been exposed
ListExploder_5 [off]
    ATTR_ACCUM_MODE = Merge Incoming List
    ATTR_CONFLICT_RES = Use Original
    INDEX_ATTR = _element_index
    LIST_ATTR = inclusion.VehicleQualifier.vehicle{}
    LIST_FOUND -> AttributeCreator_5
AttributeCreator_5
    ATTR_LIST = inclusionType,vehicle
    -> AttributeRenamer_8
AttributeRenamer_8
    ATTR_LIST = inclusion.VehicleQualifier.vehicle,inclusion,
    -> RestrictionForVehicles_Inclusion (writer GEOPACKAGE_1)

Bookmark: vehicleQualifer.load values have been exposed
ListExploder_6 [off]
    ATTR_ACCUM_MODE = Merge Incoming List
    ATTR_CONFLICT_RES = Use Original
    INDEX_ATTR = _element_index
    LIST_ATTR = inclusion.VehicleQualifier.load{}
    LIST_FOUND -> AttributeCreator_6
AttributeCreator_6
    ATTR_LIST = inclusionType,load
    -> AttributeRenamer_9
AttributeRenamer_9
    ATTR_LIST = inclusion.VehicleQualifier.load,inclusion,
    -> RestrictionForVehicles_Inclusion (writer GEOPACKAGE_1)

Bookmark: Identifies the "inclusion" "vehicleQualifer" attribute values which apply to any RestrictionForVehicle - Disabled
Note: The "exemption" attribute is populated by a vehicleQualifer data type. There are 3 attributes which contribute to the vehicleQualifer which are: / 1. Use / 2.Vehicle / 3. Load / Each of these 3 attributes have a multiplicity of 0..* so therefore need to be exposed to ensure all values populate the resulting table. This is carried out by the ListExploder transformer. / The link to this process has been disabled as there are currently no expemtions available in the product for RestrictionForVehicle features.
RestrictionForVehicles_Inclusion (writer GEOPACKAGE_1)
    attributes: TOID text(20), inclusion text(50), inclusionType text(10)

Bookmark: Add information from RoadLinks
RoadLink (reader GML_1)
    attributes: alternateIdentifier{}.ThematicIdentifier.identifier xml_char(20), alternateIdentifier{}.ThematicIdentifier.identifierScheme xml_char(39), alternateName{} xml_char(24), beginLifespanVersion xml_char(24), cycleFacility.CycleFacilityType.cycleFacility xml_char(39), cycleFacility.CycleFacilityType.cycleFacility.codeSpace xml_char(62), cycleFacility.CycleFacilityType.wholeLink xml_char(1), cycleFacility.CycleFacilityType.wholeLink.nilReason xml_char(8), cycleFacility.CycleFacilityType.wholeLink.xsi_nil xml_char(5), directionality.owns xml_char(6), directionality.xlink_href xml_char(76), elevationGain.ElevationGainType.inDirection xml_decimal(4,0), elevationGain.ElevationGainType.inDirection.uom xml_char(2), elevationGain.ElevationGainType.inOppositeDirection xml_decimal(4,0), elevationGain.ElevationGainType.inOppositeDirection.uom xml_char(2), endGradeSeparation xml_decimal(2,0), endNode.owns xml_char(6), endNode.xlink_href xml_char(22), fictitious xml_char(6), formOfWay xml_char(32), formsPartOf{}.owns xml_char(6), formsPartOf{}.xlink_href xml_char(22), inNetwork{}.owns xml_char(6), inNetwork{}.xlink_href xml_char(18), inspireId.Identifier.localId xml_decimal(17,0), inspireId.Identifier.namespace xml_char(19), length xml_decimal(7,2), length.uom xml_char(2), matchStatus xml_char(26), matchStatus.codeSpace xml_char(61),
      numberOfLanes{}.NumberOfLanesType.direction.owns xml_char(6), numberOfLanes{}.NumberOfLanesType.direction.xlink_href xml_char(76), numberOfLanes{}.NumberOfLanesType.minMaxNumberOfLanes xml_char(8), numberOfLanes{}.NumberOfLanesType.numberOfLanes xml_decimal(2,0), operationalState xml_char(5), operationalState.codeSpace xml_char(66), primaryRoute xml_char(6), provenance xml_char(16), provenance.codeSpace xml_char(66), reasonForChange xml_char(4), reasonForChange.codeSpace xml_char(47), relatedRoadArea{}.owns xml_char(6), relatedRoadArea{}.xlink_href xml_char(22), roadClassification xml_char(22), roadClassification.codeSpace xml_char(59), roadClassificationNumber xml_char(6), roadName{} xml_char(37), roadWidth.RoadWidthType.averageWidth xml_decimal(3,0), roadWidth.RoadWidthType.averageWidth.uom xml_char(2), roadWidth.RoadWidthType.confidenceLevel xml_decimal(2,0), roadWidth.RoadWidthType.minimumWidth xml_decimal(3,0), roadWidth.RoadWidthType.minimumWidth.uom xml_char(2), routeHierarchy xml_char(33), routeHierarchy.codeSpace xml_char(53), startGradeSeparation xml_decimal(2,0), startNode.owns xml_char(6), startNode.xlink_href xml_char(22), trunkRoad xml_char(6), validFrom xml_char(1), validFrom.nilReason xml_char(8),
      validFrom.xsi_nil xml_char(5), roadStructure xml_char(15)
    -> FeatureJoiner [RIGHT]
FeatureJoiner
    ATTR_CONFLICT_RES = Use Left
    GEOMETRY_HANDLING = Use Right
    JOIN_KEYS = RoadLink_TOID gml_id AUTO
    JOIN_MODE = Inner
    JOINED -> TestFilter_3
TestFilter_3
    DEFAULT_VALUE = <UNFILTERED>
    TEST_LIST = "BOOL_OP,OR,COMPOSITE_TEST,""""""<Unused>"""""",TEST_CLAUSE,TEST @Value(applicableDirection) = bothDirections",BothDirections
    BothDirections -> Clipper [CLIPPEE]
    <UNFILTERED> -> PointOnLineOverlayer [LINE]

Bookmark: Create geometry
PointOnLineOverlayer
    DEAGGREGATE_INPUT = Yes
    GROUP_BY = TOID
    TOLERANCE = 0.001
    POINT -> Bufferer
    LINE -> AttributeCreator_9
Bufferer
    ANGLE = 22.5
    CAP_STYLE = Round
    CORNER_STYLE = Round
    MODE = AREA
    OFFSET = 6
    BUFFERED -> Clipper [CLIPPER]
Clipper
    ATTR_ACCUM_MODE = Merge Clipper
    ATTR_CONFLICT_RES = Use Clippee
    BOUNDARY_CASES = Treat as Inside
    CLEANING_TOLERANCE = None
    CLIPPED_ATTR = _clipped
    CLIP_TYPE = Multiple Clippers
    CONNECT_Z_MODE = First Wins
    CREATE_AGGREGATES = Yes
    LINES_AS_SEGMENTS = No
    MEASURE_TYPE = Continuous
    MISSING_VAL_MODE = Compute
    PRESERVE_CLIPPEE_EXTENTS = No
    VAL_SOURCE = Clippee Only
    INSIDE -> DuplicateFilter
    INSIDE -> RestrictionForVehiclesLine (writer GEOPACKAGE_1)
AttributeCreator_9
    ATTR_TABLE = SET_TO radius = FME_CONDITIONAL:DEFAULT_VALUE'@Length()'BOOL_OP;OR;COMPOSITE_TEST;<Unused>;TEST @Length() > 3.01'3'FME_NUM_CONDITIONS2___
    -> TestFilter_4
TestFilter_4
    DEFAULT_VALUE = <UNFILTERED>
    TEST_LIST = "BOOL_OP,OR,COMPOSITE_TEST,""""""<Unused>"""""",TEST_CLAUSE,TEST @Value(applicableDirection) = inOppositeDirection",OppositeDirection
    OppositeDirection -> Orientor
    <UNFILTERED> -> Snipper_4
Orientor
    FLIP_APPEARANCES_CHOICE = Yes
    KIND = REVERSE
    ORIENTED -> Snipper_4
Snipper_4
    DEAGGREGATE_INPUT = YES
    ENDLOCATIONATTR = @Value(radius)
    MEASUREMENTTYPE = 2D
    SNIPMODE = Distance (Value)
    STARTLOCATIONATTR = 0
    -> DuplicateFilter
    -> RestrictionForVehiclesLine (writer GEOPACKAGE_1)
DuplicateFilter
    INPUT_ORDERED_CHOICE = No
    KEYATTR = ChainOfNetworkLinks
    UNIQUE -> Snipper
    DUPLICATE -> DuplicateFilter_2
Snipper
    DEAGGREGATE_INPUT = YES
    ENDLOCATIONATTR = 50
    MEASUREMENTTYPE = 2D
    SNIPMODE = Distance (Percentage)
    STARTLOCATIONATTR = 50
    -> RestrictionForVehiclesPoint (writer GEOPACKAGE_1)
DuplicateFilter_2
    INPUT_ORDERED_CHOICE = No
    KEYATTR = ChainOfNetworkLinks
    UNIQUE -> Snipper_2
    DUPLICATE -> Snipper_3
Snipper_2
    DEAGGREGATE_INPUT = YES
    ENDLOCATIONATTR = 25
    MEASUREMENTTYPE = 2D
    SNIPMODE = Distance (Percentage)
    STARTLOCATIONATTR = 25
    -> RestrictionForVehiclesPoint (writer GEOPACKAGE_1)
Snipper_3
    DEAGGREGATE_INPUT = YES
    ENDLOCATIONATTR = 75
    MEASUREMENTTYPE = 2D
    SNIPMODE = Distance (Percentage)
    STARTLOCATIONATTR = 75
    -> RestrictionForVehiclesPoint (writer GEOPACKAGE_1)
RestrictionForVehiclesPoint (writer GEOPACKAGE_1)
    attributes: TOID text(20), identifier text(16), restrictionType text(20), trafficSign1 text(120), trafficSign2 text(120), validFrom text(20), measure double, measure_uom text(20), sourceOfMeasure text(32), measure2 double, measure2_uom text(20), structure text(32), trafficRegulationOrder text(120), troDescription text(20), NoOfNetworkLinks smallint, ChainOfNetworkLinks text(190), Inclusion text(100), Exemption text(100), beginLifespanVersion text(20), reasonForChange text(32), chunkname text(50)
RestrictionForVehiclesLine (writer GEOPACKAGE_1)
    attributes: TOID text(20), identifier text(16), restrictionType text(20), trafficSign1 text(120), trafficSign2 text(120), validFrom text(20), measure double, measure_uom text(20), sourceOfMeasure text(32), measure2 double, measure2_uom text(20), structure text(32), trafficRegulationOrder text(120), troDescription text(20), formOfWay text(32), NoOfNetworkLinks smallint, ChainOfNetworkLinks text(190), Inclusion text(100), Exemption text(100), beginLifespanVersion text(20), reasonForChange text(32), chunkname text(50)
