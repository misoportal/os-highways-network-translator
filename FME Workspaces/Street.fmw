FME workspace Street.fmw

Parameters:
- SourceDataset_Street = $(DATA_INPUT_FOLDER)\Highways_Rrami_Street_FULL_*.gml*   # Source Street GML File(s)
- DestDataset_Street = $(MIDDLE_FOLDER)\Street.gpkg   # Middle Street Geopackage File

Readers:
- GML_1: GML from $(SourceDataset_Street)

Writers:
- GEOPACKAGE_1: GEOPACKAGE to $(DestDataset_Street)

Note: Change to local input
Street (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xsi_nil xml_boolean, link{}.nilReason xml_buffer, link{}.gml_remoteSchema xml_buffer, link{}.xlink_href xml_buffer, link{}.owns xml_boolean, geographicalName.nilReason xml_buffer, geographicalName.xsi_nil xml_boolean, geographicalName.GeographicalName.language xml_buffer, geographicalName.GeographicalName.language.nilReason xml_buffer, geographicalName.GeographicalName.language.xsi_nil xml_boolean, geographicalName.GeographicalName.nativeness.owns xml_boolean, geographicalName.GeographicalName.nativeness.nilReason xml_buffer, geographicalName.GeographicalName.nativeness.gml_remoteSchema xml_buffer, geographicalName.GeographicalName.nativeness.xlink_href xml_buffer, geographicalName.GeographicalName.nativeness.xsi_nil xml_boolean,
      geographicalName.GeographicalName.nameStatus.owns xml_boolean, geographicalName.GeographicalName.nameStatus.nilReason xml_buffer, geographicalName.GeographicalName.nameStatus.gml_remoteSchema xml_buffer, geographicalName.GeographicalName.nameStatus.xlink_href xml_buffer, geographicalName.GeographicalName.nameStatus.xsi_nil xml_boolean, geographicalName.GeographicalName.sourceOfName xml_buffer, geographicalName.GeographicalName.sourceOfName.nilReason xml_buffer, geographicalName.GeographicalName.sourceOfName.xsi_nil xml_boolean, geographicalName.GeographicalName.pronunciation.nilReason xml_buffer, geographicalName.GeographicalName.pronunciation.xsi_nil xml_boolean, geographicalName.GeographicalName.pronunciation.PronunciationOfName.pronunciationSoundLink xml_buffer, geographicalName.GeographicalName.pronunciation.PronunciationOfName.pronunciationSoundLink.nilReason xml_buffer, geographicalName.GeographicalName.pronunciation.PronunciationOfName.pronunciationSoundLink.xsi_nil xml_boolean, geographicalName.GeographicalName.pronunciation.PronunciationOfName.pronunciationIPA xml_buffer, geographicalName.GeographicalName.pronunciation.PronunciationOfName.pronunciationIPA.nilReason xml_buffer, geographicalName.GeographicalName.pronunciation.PronunciationOfName.pronunciationIPA.xsi_nil xml_boolean, geographicalName.GeographicalName.spelling{}.SpellingOfName.text xml_buffer, geographicalName.GeographicalName.spelling{}.SpellingOfName.script xml_buffer, geographicalName.GeographicalName.spelling{}.SpellingOfName.script.nilReason xml_buffer, geographicalName.GeographicalName.spelling{}.SpellingOfName.script.xsi_nil xml_boolean, geographicalName.GeographicalName.spelling{}.SpellingOfName.transliterationScheme xml_buffer, geographicalName.GeographicalName.spelling{}.SpellingOfName.transliterationScheme.nilReason xml_buffer, geographicalName.GeographicalName.spelling{}.SpellingOfName.transliterationScheme.xsi_nil xml_boolean, geographicalName.GeographicalName.grammaticalGender.owns xml_boolean, geographicalName.GeographicalName.grammaticalGender.nilReason xml_buffer, geographicalName.GeographicalName.grammaticalGender.gml_remoteSchema xml_buffer, geographicalName.GeographicalName.grammaticalGender.xlink_href xml_buffer, geographicalName.GeographicalName.grammaticalGender.xsi_nil xml_boolean, geographicalName.GeographicalName.grammaticalNumber.owns xml_boolean, geographicalName.GeographicalName.grammaticalNumber.nilReason xml_buffer,
      geographicalName.GeographicalName.grammaticalNumber.gml_remoteSchema xml_buffer, geographicalName.GeographicalName.grammaticalNumber.xlink_href xml_buffer, geographicalName.GeographicalName.grammaticalNumber.xsi_nil xml_boolean, validFrom xml_datetime, validFrom.nilReason xml_buffer, validFrom.xsi_nil xml_boolean, validTo xml_datetime, validTo.nilReason xml_buffer, validTo.xsi_nil xml_boolean, post{}.owns xml_boolean, post{}.nilReason xml_buffer, post{}.gml_remoteSchema xml_buffer, post{}.xlink_href xml_buffer, post{}.xsi_nil xml_boolean, localRoadCode xml_buffer, localRoadCode.nilReason xml_buffer, localRoadCode.xsi_nil xml_boolean, nationalRoadCode xml_buffer, nationalRoadCode.nilReason xml_buffer, nationalRoadCode.xsi_nil xml_boolean, roadClassification xml_buffer, roadClassification.codeSpace xml_buffer, designatedName{}.DesignatedNameType.name xml_buffer, designatedName{}.DesignatedNameType.name.xml_lang xml_buffer, designatedName{}.DesignatedNameType.namingAuthority.ResponsibleAuthority.identifier xml_buffer, designatedName{}.DesignatedNameType.namingAuthority.ResponsibleAuthority.authorityName xml_buffer, localName{} xml_buffer, localName{}.xml_lang xml_buffer, descriptor{} xml_buffer, descriptor{}.xml_lang xml_buffer,
      reasonForChange xml_buffer, reasonForChange.codeSpace xml_buffer, streetType xml_buffer, streetType.codeSpace xml_buffer, operationalState.OperationalStateType.state xml_buffer, operationalState.OperationalStateType.state.codeSpace xml_buffer, operationalState.OperationalStateType.validTime.nilReason xml_buffer, operationalState.OperationalStateType.validTime.gml_remoteSchema xml_buffer, operationalState.OperationalStateType.validTime.xlink_href xml_buffer, operationalState.OperationalStateType.validTime.owns xml_boolean, operationalState.OperationalStateType.validTime.gml_TimePeriod.frame xml_buffer, operationalState.OperationalStateType.validTime.gml_TimePeriod.gml_id xml_buffer, operationalState.OperationalStateType.validTime.gml_TimePeriod.gml_relatedTime{} xml_xml, operationalState.OperationalStateType.validTime.gml_TimePeriod.gml_beginPosition xml_buffer, operationalState.OperationalStateType.validTime.gml_TimePeriod.gml_beginPosition.frame xml_buffer, operationalState.OperationalStateType.validTime.gml_TimePeriod.gml_beginPosition.calendarEraName xml_buffer, operationalState.OperationalStateType.validTime.gml_TimePeriod.gml_beginPosition.indeterminatePosition xml_char(7), operationalState.OperationalStateType.validTime.gml_TimePeriod.gml_begin.nilReason xml_buffer, operationalState.OperationalStateType.validTime.gml_TimePeriod.gml_begin.gml_remoteSchema xml_buffer, operationalState.OperationalStateType.validTime.gml_TimePeriod.gml_begin.xlink_href xml_buffer, operationalState.OperationalStateType.validTime.gml_TimePeriod.gml_begin.owns xml_boolean, operationalState.OperationalStateType.validTime.gml_TimePeriod.gml_begin.gml_TimeInstant.frame xml_buffer, operationalState.OperationalStateType.validTime.gml_TimePeriod.gml_begin.gml_TimeInstant.gml_id xml_buffer, operationalState.OperationalStateType.validTime.gml_TimePeriod.gml_begin.gml_TimeInstant.gml_relatedTime{} xml_xml, operationalState.OperationalStateType.validTime.gml_TimePeriod.gml_begin.gml_TimeInstant.gml_timePosition xml_buffer, operationalState.OperationalStateType.validTime.gml_TimePeriod.gml_begin.gml_TimeInstant.gml_timePosition.frame xml_buffer, operationalState.OperationalStateType.validTime.gml_TimePeriod.gml_begin.gml_TimeInstant.gml_timePosition.calendarEraName xml_buffer, operationalState.OperationalStateType.validTime.gml_TimePeriod.gml_begin.gml_TimeInstant.gml_timePosition.indeterminatePosition xml_char(7), operationalState.OperationalStateType.validTime.gml_TimePeriod.gml_endPosition xml_buffer, operationalState.OperationalStateType.validTime.gml_TimePeriod.gml_endPosition.frame xml_buffer,
      operationalState.OperationalStateType.validTime.gml_TimePeriod.gml_endPosition.calendarEraName xml_buffer, operationalState.OperationalStateType.validTime.gml_TimePeriod.gml_endPosition.indeterminatePosition xml_char(7), operationalState.OperationalStateType.validTime.gml_TimePeriod.gml_end.nilReason xml_buffer, operationalState.OperationalStateType.validTime.gml_TimePeriod.gml_end.gml_remoteSchema xml_buffer, operationalState.OperationalStateType.validTime.gml_TimePeriod.gml_end.xlink_href xml_buffer, operationalState.OperationalStateType.validTime.gml_TimePeriod.gml_end.owns xml_boolean, operationalState.OperationalStateType.validTime.gml_TimePeriod.gml_end.gml_TimeInstant.frame xml_buffer, operationalState.OperationalStateType.validTime.gml_TimePeriod.gml_end.gml_TimeInstant.gml_id xml_buffer, operationalState.OperationalStateType.validTime.gml_TimePeriod.gml_end.gml_TimeInstant.gml_relatedTime{} xml_xml, operationalState.OperationalStateType.validTime.gml_TimePeriod.gml_end.gml_TimeInstant.gml_timePosition xml_buffer, operationalState.OperationalStateType.validTime.gml_TimePeriod.gml_end.gml_TimeInstant.gml_timePosition.frame xml_buffer, operationalState.OperationalStateType.validTime.gml_TimePeriod.gml_end.gml_TimeInstant.gml_timePosition.calendarEraName xml_buffer, operationalState.OperationalStateType.validTime.gml_TimePeriod.gml_end.gml_TimeInstant.gml_timePosition.indeterminatePosition xml_char(7), operationalState.OperationalStateType.validTime.gml_TimePeriod.gml_duration xml_buffer, operationalState.OperationalStateType.validTime.gml_TimePeriod.gml_timeInterval xml_real64, operationalState.OperationalStateType.validTime.gml_TimePeriod.gml_timeInterval.unit xml_buffer, operationalState.OperationalStateType.validTime.gml_TimePeriod.gml_timeInterval.radix xml_uint64, operationalState.OperationalStateType.validTime.gml_TimePeriod.gml_timeInterval.factor xml_int64, operationalState.OperationalStateType.reason xml_buffer, locality{} xml_buffer, locality{}.xml_lang xml_buffer, town{} xml_buffer, town{}.xml_lang xml_buffer, administrativeArea{} xml_buffer, administrativeArea{}.xml_lang xml_buffer, responsibleAuthority.ResponsibleAuthority.identifier xml_buffer, responsibleAuthority.ResponsibleAuthority.authorityName xml_buffer, geometryProvenance xml_buffer, geometryProvenance.codeSpace xml_buffer, geometry xml_geometry,
      gssCode{}.nilReason xml_buffer, gssCode{}.gml_remoteSchema xml_buffer, gssCode{}.xlink_href xml_buffer, gssCode{}.owns xml_boolean
    -> AttributeRenamer_8
AttributeRenamer_8
    ATTR_LIST = gml_id,USRN,,inspireId.Identifier.localId,identifier,,fme_basename,chunkname,
    -> ListExploder
    -> ListIndexer

Bookmark: Identifies the RoadLinks which are a part of the Street feature
ListExploder
    ATTR_ACCUM_MODE = Merge Incoming List
    ATTR_CONFLICT_RES = Use Original
    INDEX_ATTR = _element_index
    LIST_ATTR = link{}
    LIST_FOUND -> AttributeRenamer_15
Note: Relates street to road link geometry
AttributeRenamer_15
    ATTR_LIST = xlink_href,RoadLink_TOID,
    -> StringReplacer
Note: remove # from the / feature references
StringReplacer
    CASE = no
    FIND_TEXT = #
    NO_MATCH = _FME_NO_OP_
    REGEXP = no
    SRC_ATTRS = RoadLink_TOID
    -> Street_NetworkRef (writer GEOPACKAGE_1)
Street_NetworkRef (writer GEOPACKAGE_1)
    attributes: USRN text(20), RoadLink_TOID text(20)

Bookmark: designatedName
Note: designatedName1
ListIndexer
    INDEX = 0
    LIST_ATTR = designatedName{}
    PREFIX = designatedName1_
    -> AttributeRenamer_2
Note: designatedName1
AttributeRenamer_2
    ATTR_LIST = designatedName1_DesignatedNameType.name,designatedName1,,designatedName1_DesignatedNameType.name.xml_lang,designatedName1_Language,,designatedName1_DesignatedNameType.namingAuthority.ResponsibleAuthority.authorityName,designatedName1_Authority,,designatedName1_DesignatedNameType.namingAuthority.ResponsibleAuthority.identifier,designatedName1_AuthorityID,
    -> ListIndexer_2
Note: designatedName2
ListIndexer_2
    INDEX = 1
    LIST_ATTR = designatedName{}
    PREFIX = designatedName2_
    -> AttributeRenamer_3
Note: designatedName2
AttributeRenamer_3
    ATTR_LIST = designatedName2_DesignatedNameType.name,designatedName2,,designatedName2_DesignatedNameType.name.xml_lang,designatedName2_Language,,designatedName2_DesignatedNameType.namingAuthority.ResponsibleAuthority.authorityName,designatedName2_Authority,,designatedName2_DesignatedNameType.namingAuthority.ResponsibleAuthority.identifier,designatedName2_AuthorityID,
    -> ListIndexer_3

Bookmark: descriptor
Note: descriptor1
ListIndexer_3
    INDEX = 0
    LIST_ATTR = descriptor{}
    PREFIX = descriptor1_
    -> AttributeRenamer_4
Note: descriptor1
AttributeRenamer_4
    ATTR_LIST = descriptor1_descriptor,descriptor1,,descriptor1_xml_lang,descriptor1_Language,
    -> ListIndexer_4
Note: descriptor2
ListIndexer_4
    INDEX = 1
    LIST_ATTR = descriptor{}
    PREFIX = descriptor2_
    -> AttributeRenamer_5
Note: descriptor2
AttributeRenamer_5
    ATTR_LIST = descriptor2_descriptor,descriptor2,,descriptor2_xml_lang,descriptor2_Language,
    -> ListIndexer_5

Bookmark: localName
Note: localName1
ListIndexer_5
    INDEX = 0
    LIST_ATTR = localName{}
    PREFIX = localName1_
    -> AttributeRenamer_6
Note: localName1
AttributeRenamer_6
    ATTR_LIST = localName1_localName,localName1,,localName1_xml_lang,localName1_Language,
    -> ListIndexer_6
Note: localName2
ListIndexer_6
    INDEX = 1
    LIST_ATTR = localName{}
    PREFIX = localName2_
    -> AttributeRenamer_7
Note: localName2
AttributeRenamer_7
    ATTR_LIST = localName2_localName,localName2,,localName2_xml_lang,localName2_Language,
    -> ListIndexer_7

Bookmark: locality
Note: locality 1
ListIndexer_7
    INDEX = 0
    LIST_ATTR = locality{}
    PREFIX = locality1_
    -> AttributeRenamer_9
Note: locality 1
AttributeRenamer_9
    ATTR_LIST = locality1_locality,locality1,,locality1_xml_lang,locality1_Language,
    -> ListIndexer_8
Note: locality 2
ListIndexer_8
    INDEX = 1
    LIST_ATTR = localName{}
    PREFIX = localitName2_
    -> AttributeRenamer_10
Note: locality 2
AttributeRenamer_10
    ATTR_LIST = localityName2_localName,locality2,,localityName2_xml_lang,locality2_Language,
    -> ListIndexer_9

Bookmark: administrativeArea
Note: adminArea 1
ListIndexer_9
    INDEX = 0
    LIST_ATTR = administrativeArea{}
    PREFIX = administrative_area1_
    -> AttributeRenamer_11
Note: adminArea 1
AttributeRenamer_11
    ATTR_LIST = administrative_area1_administrativeArea,administrativeArea1,,administrative_area1_xml_lang,administrativeArea1_Language,
    -> ListIndexer_10
Note: adminArea 2
ListIndexer_10
    INDEX = 1
    LIST_ATTR = administrativeArea{}
    PREFIX = administrative_area2_
    -> AttributeRenamer_12
Note: adminArea 2
AttributeRenamer_12
    ATTR_LIST = administrative_area2_administrativeArea,administrativeArea2,,administrative_area2_xml_lang,administrativeArea2_Language,
    -> ListIndexer_11

Bookmark: town
Note: town 1
ListIndexer_11
    INDEX = 0
    LIST_ATTR = town{}
    PREFIX = town1_
    -> AttributeRenamer_13
Note: town 1
AttributeRenamer_13
    ATTR_LIST = town1_town,town1,,town1_xml_lang,town1_Language,
    -> ListIndexer_12
Note: town 2
ListIndexer_12
    INDEX = 1
    LIST_ATTR = town{}
    PREFIX = town2_
    -> AttributeRenamer_14
Note: town 2
AttributeRenamer_14
    ATTR_LIST = town2_town,town2,,town2_xml_lang,town2_Language,
    -> AttributeRenamer

Bookmark: Creates the Street feature
Note: Using lists to expose attributes which have a multiplicity greater than 1 and listing them as seperate attributes.
Note: This is an example output, writer will need to be added for specific output
AttributeRenamer
    ATTR_LIST = inspireId.Identifier.localId,localId,,inspireId.Identifier.versionId,versionId,,operationalState.OperationalStateType.state,operationalState_State,,operationalState.OperationalStateType.reason,operationsState_Reason,,operationalState.OperationalStateType.validTime.gml_TimePeriod.gml_beginPosition,operationalState_StartTime,,operationalState.OperationalStateType.validTime.gml_TimePeriod.gml_endPosition,operationalState_EndTime,,onsCode.xlink_href,onsCode,,area.xlink_href,area,,administrativeUnit.xlink_href,administrativeUnit,,town.xlink_href,town,,locality.xlink_href,locality,,responsibleAuthority.ResponsibleAuthority.identifier,responsibleAuthority_AuthorityID,,responsibleAuthority.ResponsibleAuthority.authorityName,responsibleAuthority_Authority,,gssCode{0}.xlink_href,gssCode1,,gssCode{1}.xlink_href,gssCode2,
    -> AttributeTrimmer
AttributeTrimmer
    SRC_ATTRS = gssCode1,gssCode2
    TRIM_CHARS = #
    TRIM_TO_NONE = Yes
    TRIM_TYPE = Both
    -> DateFormatter
Note: Format date as DMY
DateFormatter
    DATE_ATTR = beginLifespanVersion,operationalState_StartTime,validFrom,validTo
    FMT = FME Date (%Y%m%d)
    INVALID_DATE_VALUE = _FME_NO_OP_
    SRCFMT = Unknown - Automatic Detection
    -> ListElementCounter

Bookmark: miso addition
ListElementCounter
    CNT_ATTR = NationalNetworkLinks
    LIST_NAME = link{}
    -> TestFilter
TestFilter
    DEFAULT_VALUE = <UNFILTERED>
    TEST_LIST = "BOOL_OP,OR,COMPOSITE_TEST,""""""<Unused>"""""",TEST_CLAUSE,CASE_INSENSITIVE_TEST @Value(streetType) CONTAINS Numbered Street",Numbered
    <UNFILTERED> -> Street_Named (writer GEOPACKAGE_1)
    Numbered -> Street_Numbered (writer GEOPACKAGE_1)
Street_Numbered (writer GEOPACKAGE_1)
    attributes: USRN text(20), identifier text(37), localRoadCode text(48), nationalRoadCode text(10), descriptor1 text(120), descriptor1_Language text(10), descriptor2 text(120), descriptor2_Language text(10), roadClassification text(21),indexed, streetType text(35), operationalState_State text(20), operationsState_Reason text(120), operationalState_StartTime text(20), operationalState_EndTime text(20), locality1 text(35), locality1_Language text(20), locality2 text(35), locality2_Language text(20), town1 text(30), town1_Language text(10), town2 text(30), town2_Language text(10), responsibleAuthority_AuthorityID text(4), responsibleAuthority_Authority text(120), administrativeArea1 text(30), administrativeArea1_Language text(10), administrativeArea2 text(30), administrativeArea2_Language text(10), gssCode1 text(10), gssCode2 text(10),
      geometryProvenance text(30), NationalNetworkLinks mediumint, beginLifespanVersion text(20), reasonForChange text(32), validFrom text(20), chunkname text(50)
Street_Named (writer GEOPACKAGE_1)
    attributes: USRN text(20), identifier text(37), descriptor1 text(120), descriptor1_Language text(10), descriptor2 text(120), descriptor2_Language text(10), designatedName1 text(120), designatedName1_Language text(10), designatedName1_AuthorityID text(4), designatedName1_Authority text(120), designatedName2 text(120), designatedName2_Language text(10), designatedName2_AuthorityID text(4), designatedName2_Authority text(120), localName1 text(120), localName1_Language text(10), localName2 text(120), localName2_Language text(10), roadClassification text(21),indexed, streetType text(35), operationalState_State text(20), operationsState_Reason text(120), operationalState_StartTime text(20), operationalState_EndTime text(20), locality1 text(35), locality1_Language text(20), locality2 text(35), locality2_Language text(20), town1 text(30), town1_Language text(10),
      town2 text(30), town2_Language text(10), responsibleAuthority_AuthorityID text(4), responsibleAuthority_Authority text(120), administrativeArea1 text(30), administrativeArea1_Language text(10), administrativeArea2 text(30), administrativeArea2_Language text(10), gssCode1 text(10), gssCode2 text(10), geometryProvenance text(30), NationalNetworkLinks mediumint, beginLifespanVersion text(20), reasonForChange text(32), validFrom text(20), chunkname text(50)
